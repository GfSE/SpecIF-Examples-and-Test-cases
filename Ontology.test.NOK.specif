# SpecIF Ontology
The SpecIF ontology collects terms used in the domain of systems engineering and requirements management. Agreed-upon terms help both collaborators to communicate more clearly and systems to match data fields automatically.
- Rights: Creative Commons 4.0 CC BY-SA, https://creativecommons.org/licenses/by-sa/4.0/

## SpecIF Ontology (SpecIF:Heading)
- dcterms:type: W3C:Ontology

## Introduction (SpecIF:Heading)
- dcterms:description: The SpecIF Vocabulary (or Glossary) collects terms used in the domain of systems engineering and requirements management. Agreed-upon terms help both collaborators to communicate more clearly and systems to match data fields automatically. SpecIF adopts terms and their definitions from other initiatives, for example from the Dublin Core Metadata Initiative (DCMI), the Open Services for Lifecycle Collaboration (OSLC) and the International Requirements Engineering Board (IREB). The ProSTEP iViP association has also defined a set of attribute names to be used in ReqIF data, but those are not freely available and cannot be referenced here.
  All terms carry a namespace, which is the first part separated with ':' or '.' ― they are thus easily recognized in text and data fields. For display, systems may choose to replace SpecIF terms by domain or language specific words. This collection itself is structured according to SpecIF using it's vocabulary. Hence, the titles are recognized as such, because they are tagged with "[[dcterms:title]]", whereas paragraphs like this one are tagged with "[[dcterms:description]]".
  The terms have a lifecycle status as follows:
  - experimental: The term is being used in first projects, but has not yet any normative maturity.
  - submitted: The term has been submitted for adoption.
  - released: The term has been adopted for use with SpecIF and is preferred among equivalent terms.
  - equivalent: The term has been adopted for use with SpecIF, but the released term is preferred.
  - deprecated: The term shall not any more be used with SpecIF; use the released term.
  The Specification Interchange Facility (SpecIF) is the result of an initiative by the Gesellschaft für Systems Engineering (GfSE), the German chapter of The International Council on Systems Engineering (INCOSE).
  All information provided here is made available according to Creative Commons 4.0 CC BY-SA or the license chosen by the respective publishers. We appreciate any contribution or proposal; please contact Dr. Oskar von Dungern.
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
## Namespaces (SpecIF:Heading)

## SpecIF: (SpecIF:Namespace)
- SpecIF:Origin: https://specif.de

## IREB: (SpecIF:Namespace)
- SpecIF:Origin: https://www.ireb.org/en/downloads/#cpre-glossary

## ReqIF. (SpecIF:Namespace)
- SpecIF:Origin: https://www.prostep.org/fileadmin/downloads/Recommendation_ReqIF_V2_RZ3.pdf

## Archimate: (SpecIF:Namespace)
- SpecIF:Origin: https://pubs.opengroup.org

## Resource Class Terms (SpecIF:Heading)
- dcterms:description: A resource represents an artefact, e.g. a model element or a requirement. The terms listed in this chapter may be used to distinguish different classes (types) of artefacts constituting a system specification. A resource may serve as subject or as object in a subject-predicate-object statement. Each resource class may define an individual set of properties for carrying the information 'payload'.
  A resource class corresponds to a 'SPEC-OBJECT-TYPE' and a resource is a 'SPEC-OBJECT' in the Requirements Interchange Format (ReqIF). In ArchiMate® 3.0, a resource is an Element.

## SpecIF:Paragraph (SpecIF:TermResourceClass)
- dcterms:identifier: RC-Paragraph
- SpecIF:Revision: 1.1
- dcterms:description: A 'Paragraph' is an unspecified information in a document at any level.
- SpecIF:Domain: Base, Requirement Engineering, Automotive Stakeholder Request Clarification Process, System Model Integration
- SpecIF:LifecycleStatus: SpecIF:LifecycleStatusReleased
- SpecIF:LocalTerm: Paragraph
- SpecIF:isHeading: false
- SpecIF:Instantiation: auto, user

## SpecIF:Heading (SpecIF:TermResourceClass)
- dcterms:identifier: RC-Folder
- SpecIF:Revision: 1.1
- dcterms:description: A 'Heading' is a chapter title at any level.
- SpecIF:Domain: Base, Requirement Engineering, Automotive Stakeholder Request Clarification Process, System Model Integration
- SpecIF:LifecycleStatus: SpecIF:LifecycleStatusReleased
- SpecIF:LocalTerm: Kapitelüberschrift
- SpecIF:isHeading: true
- SpecIF:Instantiation: auto, user

## SpecIF:View (SpecIF:TermResourceClass)
- SpecIF:Revision: 1.2
- SpecIF:LocalTerm: Model Diagram
- SpecIF:LocalTermPlural: Model Diagrams
- dcterms:description: A 'View' is a graphical model view with a specific communication purpose, e.g. a business process or system composition.
- SpecIF:Origin: http://specif.de
- SpecIF:Domain: System Model Integration
- SpecIF:LifecycleStatus: SpecIF:LifecycleStatusReleased
- SpecIF:Icon: ▣
- SpecIF:isHeading: false
- SpecIF:Instantiation: auto

## ArchiMate:Viewpoint (SpecIF:TermResourceClass)
- SpecIF:Revision: 1.2
- SpecIF:LocalTerm: Model Diagram
- SpecIF:LocalTermPlural: Model Diagrams
- dcterms:description: A viewpoint in the ArchiMate language is a selection of a relevant subset of the ArchiMate elements and their relationships. This is the representation of that part of an architecture that is expressed in different diagrams.
- SpecIF:Origin: https://pubs.opengroup.org/architecture/archimate3-doc/apdxc.html
- SpecIF:Domain: System Model Integration
- SpecIF:LifecycleStatus: SpecIF:LifecycleStatusEquivalent
- SpecIF:Icon: ▣
- SpecIF:isHeading: false
- SpecIF:Instantiation: auto

## SpecIF:Diagram (SpecIF:TermResourceClass)
- SpecIF:LocalTerm: Model Diagram
- SpecIF:LocalTermPlural: Model Diagrams
- dcterms:description: A 'Diagram' is a graphical model view with a specific communication purpose, e.g. a business process or system composition.
- SpecIF:Origin: http://specif.de
- SpecIF:Domain: System Model Integration
- SpecIF:LifecycleStatus: SpecIF:LifecycleStatusDeprecated
- SpecIF:isHeading: false

## SpecIF:Feature (SpecIF:TermResourceClass)
- SpecIF:Revision: 1.2
- SpecIF:LocalTerm: Feature
- dcterms:description: A 'Feature' is an intentional distinguishing characteristic of a system, often a unique selling proposition.
- SpecIF:Origin: http://specif.de
- SpecIF:Domain: Requirement Engineering, Automotive Stakeholder Request Clarification Process, System Model Integration
- SpecIF:LifecycleStatus: SpecIF:LifecycleStatusDeprecated
- SpecIF:Icon: ✶
- SpecIF:isHeading: false
- SpecIF:Instantiation: user

## IREB:Requirement (SpecIF:TermResourceClass)
- dcterms:identifier: RC-Requirement
- SpecIF:Revision: 1.2
- dcterms:description: A 'Requirement' is a singular documented physical and functional need that a particular design, product or process must be able to perform. (source: Wikipedia)
  Definition:
  1. A condition or capability needed by a user to solve a problem or achieve an objective.
  2. A condition or capability that must be met or possessed by a system or system component to satisfy a contract, standard, specification, or other formally imposed documents.
  3. A documented representation of a condition or capability as in (1) or (2).
  Note: The definition above is the classic one from IEEE Std 610.12 of 1990. Alternatively, we also give a more modern definition:
  1. A need perceived by a stakeholder.
  2. A capability or property that a system shall have.
  3. A documented representation of a need, capability or property.
- SpecIF:LocalTerm: Requirement
- SpecIF:LocalTermPlural: Requirements
- SpecIF:Origin: https://www.ireb.org/en/downloads/#cpre-glossary
- SpecIF:Domain: Requirement Engineering
- SpecIF:LifecycleStatus: SpecIF:LifecycleStatusReleased
- SpecIF:Icon: ❢
- SpecIF:isHeading: false
- SpecIF:Instantiation: user

## ReqIF-WF:Requirement (SpecIF:TermResourceClass)
- SpecIF:Revision: 1.2
- SpecIF:LocalTerm: Requirement
- SpecIF:LocalTermPlural: Requirements
- dcterms:description: A 'Requirement' is a singular documented physical and functional need that a particular design, product or process must be able to perform. (source: Wikipedia)
  Definition:
  1. A condition or capability needed by a user to solve a problem or achieve an objective.
  2. A condition or capability that must be met or possessed by a system or system component to satisfy a contract, standard, specification, or other formally imposed documents.
  3. A documented representation of a condition or capability as in (1) or (2).
  Note: The definition above is the classic one from IEEE Std 610.12 of 1990. Alternatively, we also give a more modern definition:
  1. A need perceived by a stakeholder.
  2. A capability or property that a system shall have.
  3. A documented representation of a need, capability or property.
- SpecIF:Origin: https://www.ireb.org/en/downloads/#cpre-glossary
- SpecIF:Domain: Automotive Stakeholder Request Clarification Process
- SpecIF:LifecycleStatus: SpecIF:LifecycleStatusReleased
- SpecIF:Icon: ❢
- SpecIF:isHeading: false
- SpecIF:Instantiation: user

## SpecIF:ModelElement (SpecIF:TermResourceClass)
- SpecIF:Revision: 1.2
- SpecIF:Origin: https://specif.de
- SpecIF:Domain: System Model Integration
- SpecIF:LifecycleStatus: SpecIF:LifecycleStatusReleased
- SpecIF:isHeading: false

## FMC:Plan (SpecIF:TermResourceClass)
- dcterms:description: A 'Plan' is a graphical model view with a specific communication purpose, e.g. a business process or system composition.
- SpecIF:Origin: http://fmc-modeling.org/
- SpecIF:LifecycleStatus: SpecIF:LifecycleStatusEquivalent

## FMC:Actor (SpecIF:TermResourceClass)
- dcterms:identifier: RC-Actor
- SpecIF:Revision: 1.2
- SpecIF:LocalTerm: Actor
- SpecIF:LocalTermPlural: Actors
- dcterms:description: An 'Actor' is a fundamental model element type representing an active entity, be it an activity, a process step, a function, a system component or a role.
  The particular use of FMC:Actor is specified with a [[dcterms:type]] property. The values of that property can be ontology-terms, such as [[bpmn:timer]].
- SpecIF:Origin: http://fmc-modeling.org/
- SpecIF:Domain: System Model Integration
- SpecIF:LifecycleStatus: SpecIF:LifecycleStatusReleased
- SpecIF:Icon: ■
- SpecIF:isHeading: false
- SpecIF:Instantiation: auto

## FMC:State (SpecIF:TermResourceClass)
- dcterms:identifier: RC-State
- SpecIF:Revision: 1.2
- SpecIF:LocalTerm: State
- SpecIF:LocalTermPlural: States
- dcterms:description: A 'State' is a fundamental model element type representing a passive entity, be it a value, a condition, an information storage or even a physical shape.
- SpecIF:Origin: http://fmc-modeling.org/
- SpecIF:Domain: System Model Integration
- SpecIF:LifecycleStatus: SpecIF:LifecycleStatusReleased
- SpecIF:Icon: ●
- SpecIF:isHeading: false
- SpecIF:Instantiation: auto

## FMC:Event (SpecIF:TermResourceClass)
- dcterms:identifier: RC-Event
- SpecIF:Revision: 1.2
- SpecIF:LocalTerm: Event
- SpecIF:LocalTermPlural: Events
- dcterms:description: An 'Event' is a fundamental model element type representing a time reference, a change in condition/value or more generally a synchronization primitive.
- SpecIF:Origin: http://fmc-modeling.org/
- SpecIF:Domain: System Model Integration
- SpecIF:LifecycleStatus: SpecIF:LifecycleStatusReleased
- SpecIF:Icon: ⬧
- SpecIF:isHeading: false
- SpecIF:Instantiation: auto

## SpecIF:Collection (SpecIF:TermResourceClass)
- dcterms:identifier: RC-Collection
- SpecIF:Revision: 1.2
- SpecIF:LocalTerm: Collection or Group
- SpecIF:LocalTermPlural: Collections and Groups
- dcterms:description: A 'Collection' is a logic (often conceptual) group of resources linked with a [[SpecIF:contains]] statement. It corresponds to a 'Group' in BPMN Diagrams.
  BPMN: An arbitrary set of objects can be defined as a Group to show that they logically belong together. (source: BPMN Tutorial)
- SpecIF:Origin: http://specif.de
- SpecIF:Domain: System Model Integration
- SpecIF:LifecycleStatus: SpecIF:LifecycleStatusReleased
- SpecIF:Icon: ⬚
- SpecIF:isHeading: false
- SpecIF:Instantiation: auto

## bpmn:group (SpecIF:TermResourceClass)
- dcterms:description: BPMN: An arbitrary set of objects can be defined as a Group to show that they logically belong together. Like all BPMN 'artifacts', a group does not influence execution semantics. In PBMN, a group can be freely applied, even across pool boundaries. (source: BPMN Reference)
- SpecIF:Origin: https://camunda.com/bpmn/reference/
- SpecIF:LifecycleStatus: SpecIF:LifecycleStatusExperimental

## SpecIF:Comment (SpecIF:TermResourceClass)
- dcterms:identifier: RC-Comment
- SpecIF:Revision: 1.1
- dcterms:description: A 'Comment' is reader feedback referring to a model element ('resource' or 'statement' in general).
- SpecIF:Origin: http://specif.de
- SpecIF:Domain: Base
- SpecIF:LifecycleStatus: SpecIF:LifecycleStatusReleased
- SpecIF:Icon: 🗅
- SpecIF:isHeading: false
- SpecIF:Instantiation: auto

## SpecIF:Note (SpecIF:TermResourceClass)
- dcterms:identifier: RC-Note
- SpecIF:Revision: 1.1
- dcterms:description: A 'Note' is additional information by the author referring to any resource.
- SpecIF:Origin: http://specif.de
- SpecIF:LifecycleStatus: SpecIF:LifecycleStatusReleased
- SpecIF:isHeading: false
- SpecIF:Instantiation: user

## SpecIF:Issue (SpecIF:TermResourceClass)
- dcterms:description: An 'Issue' is a question to answer or decision to take which is worth tracking.
- SpecIF:Origin: http://specif.de
- SpecIF:Domain: Issue Management
- SpecIF:LifecycleStatus: SpecIF:LifecycleStatusReleased

## SpecIF:OntologyTerm (SpecIF:TermResourceClass)
- SpecIF:Revision: 1.2
- SpecIF:Origin: https://specif.de
- SpecIF:Domain: Ontology
- SpecIF:LifecycleStatus: SpecIF:LifecycleStatusReleased
- SpecIF:isHeading: false

## SpecIF:TermResourceClass (SpecIF:TermResourceClass)
- SpecIF:Revision: 1.2
- dcterms:description: A term for SpecIF resources, often used as title of a resourceClass to denote the class type.
- SpecIF:Domain: Ontology
- SpecIF:LifecycleStatus: SpecIF:LifecycleStatusReleased
- SpecIF:isHeading: false
- SpecIF:Instantiation: user

## SpecIF:TermStatementClass (SpecIF:TermResourceClass)
- SpecIF:Revision: 1.2
- dcterms:description: A term for SpecIF statements, often used as title of a statementClass to denote the class type.
- SpecIF:Domain: Ontology
- SpecIF:LifecycleStatus: SpecIF:LifecycleStatusReleased
- SpecIF:isHeading: false
- SpecIF:Instantiation: user

## SpecIF:TermPropertyClass (SpecIF:TermResourceClass)
- SpecIF:Revision: 1.2
- dcterms:description: A term for SpecIF properties, often used as title of a propertyClass to denote the class type.
- SpecIF:Domain: Ontology
- SpecIF:LifecycleStatus: SpecIF:LifecycleStatusReleased
- SpecIF:isHeading: false
- SpecIF:Instantiation: user

## SpecIF:TermPropertyValue (SpecIF:TermResourceClass)
- SpecIF:Revision: 1.2
- dcterms:description: A term for SpecIF property values, often used in enumerated dataTypes.
- SpecIF:Domain: Ontology
- SpecIF:LifecycleStatus: SpecIF:LifecycleStatusReleased
- SpecIF:isHeading: false
- SpecIF:Instantiation: user

## IREB:Risk (SpecIF:TermResourceClass)
- dcterms:description: An event that threatens the success of an endeavor, e.g., of developing or operating a system. A risk is typically assessed in terms of its probability and potential damage.
- SpecIF:Origin: https://www.ireb.org/en/downloads/#cpre-glossary
- SpecIF:LifecycleStatus: SpecIF:LifecycleStatusReleased
- SpecIF:isHeading: false

## foaf:Person (SpecIF:TermResourceClass)
- dcterms:description: The Person class represents people. Something is a Person if it is a person. We don't nitpic about whether they're alive, dead, real, or imaginary. (source: FOAF)
- SpecIF:Origin: http://xmlns.com/foaf/
- SpecIF:LifecycleStatus: SpecIF:LifecycleStatusReleased

## SpecIF:Hierarchy (SpecIF:TermResourceClass)
- dcterms:description: A root of a document structure with references to resources.
- SpecIF:Origin: http://specif.de
- SpecIF:LifecycleStatus: SpecIF:LifecycleStatusEquivalent
- SpecIF:isHeading: false

## SpecIF:Outline (SpecIF:TermResourceClass)
- SpecIF:Revision: 1.2
- dcterms:description: A root of a document structure with references to resources.
- SpecIF:Origin: http://specif.de
- SpecIF:Domain: Base, Requirement Engineering, Automotive Stakeholder Request Clarification Process, System Model Integration
- SpecIF:LifecycleStatus: SpecIF:LifecycleStatusReleased
- SpecIF:isHeading: true
- SpecIF:Instantiation: user

## SpecIF:BillOfMaterials (SpecIF:TermResourceClass)
- SpecIF:Revision: 1.2
- dcterms:description: A bill of materials or product structure (sometimes bill of material, BOM or associated list) is a list of the raw materials, sub-assemblies, intermediate assemblies, sub-components, parts and the quantities of each needed to manufacture an end product. A BOM may be used for communication between manufacturing partners, or confined to a single manufacturing plant. (source: Wikipedia)
- SpecIF:Origin: http://specif.de
- SpecIF:Domain: System Model Integration
- SpecIF:LifecycleStatus: SpecIF:LifecycleStatusReleased
- SpecIF:isHeading: true
- SpecIF:Instantiation: user

## SpecIF:BusinessProcess (SpecIF:TermResourceClass)
- SpecIF:Revision: 1.2
- SpecIF:Origin: http://specif.de
- SpecIF:Domain: System Model Integration
- SpecIF:LifecycleStatus: SpecIF:LifecycleStatusReleased
- SpecIF:LocalTerm: Business Process
- SpecIF:LocalTermPlural: Business Processes
- SpecIF:isHeading: false
- SpecIF:Instantiation: auto

## SpecIF:BusinessProcesses (SpecIF:TermResourceClass)
- SpecIF:Revision: 1.2
- SpecIF:Origin: http://specif.de
- SpecIF:Domain: System Model Integration
- SpecIF:LifecycleStatus: SpecIF:LifecycleStatusReleased
- SpecIF:LocalTerm: Business Processes
- SpecIF:isHeading: true
- SpecIF:Instantiation: auto

## SpecIF:Glossary (SpecIF:TermResourceClass)
- SpecIF:Revision: 1.2
- SpecIF:LocalTerm: Model Elements (Glossary)
- dcterms:description: tbd
- SpecIF:Origin: https://specif.de
- SpecIF:Domain: Ontology
- SpecIF:LifecycleStatus: SpecIF:LifecycleStatusReleased
- SpecIF:isHeading: true
- SpecIF:Instantiation: user

## SpecIF:UnreferencedResources (SpecIF:TermResourceClass)
- SpecIF:Revision: 1.2
- SpecIF:Origin: https://specif.de
- SpecIF:Domain: Base
- SpecIF:LifecycleStatus: SpecIF:LifecycleStatusReleased
- SpecIF:LocalTerm: Unreferenced Resources (Recycle Bin)
- SpecIF:isHeading: true
- SpecIF:Instantiation: auto

## W3C:Vocabulary (SpecIF:TermResourceClass)
- SpecIF:Revision: 1.2
- SpecIF:LocalTerm: Vocabulary
- dcterms:description: A vocabulary according to the SpecIF class definitions for the domain 'Ontology'.

  There is no clear division between what is referred to as “vocabularies” and “ontologies”. The trend is to use the word “ontology” for more complex, and possibly quite formal collection of terms, whereas “vocabulary” is used when such strict formalism is not necessarily used or only in a very loose sense. Vocabularies are the basic building blocks for inference techniques on the Semantic Web.
- SpecIF:Origin: https://www.w3.org/standards/semanticweb/ontology
- SpecIF:Domain: Ontology
- SpecIF:LifecycleStatus: SpecIF:LifecycleStatusEquivalent
- SpecIF:isHeading: true
- SpecIF:Instantiation: user

## W3C:Ontology (SpecIF:TermResourceClass)
- SpecIF:Revision: 1.2
- SpecIF:LocalTerm: Ontology
- dcterms:description: An ontology according to the SpecIF class definitions for the domain 'Ontology'.

  There is no clear division between what is referred to as “vocabularies” and “ontologies”. The trend is to use the word “ontology” for more complex, and possibly quite formal collection of terms, whereas “vocabulary” is used when such strict formalism is not necessarily used or only in a very loose sense. Vocabularies are the basic building blocks for inference techniques on the Semantic Web.
- SpecIF:Origin: https://www.w3.org/standards/semanticweb/ontology
- SpecIF:Domain: Ontology
- SpecIF:LifecycleStatus: SpecIF:LifecycleStatusReleased
- SpecIF:isHeading: true
- SpecIF:Instantiation: user

## Statement Class Terms (SpecIF:Heading)
- dcterms:description: A statement represents a logic affinity or association between two resources, i.e. system specification artefacts. The terms listed in this chapter may be used as predicates to distinguish different classes (types) of statements. Each statement class may define an individual set of properties for carrying the information 'payload'.
  In SpecIF, a statement is first order predicate logic. For each predicate (statement class), a list of eligible resource classes may be defined for subjects and objects, respectively. For example, the predicate [[oslc_rm:satisfies]] is usually confined to [[FMC:Actor]] and [[FMC:State]] as subject and [[IREB:Requirement]] as object.
  A statement consisting of subject-predicate-object (where a resource may serve as subject or object) can be directly mapped to a ReqIF relation, a RDF triple in OSLC or 'linked data' in general.
  A statement class corresponds to a 'SPEC-RELATION-TYPE' and a statement is a 'SPEC-RELATION' in the Requirements Interchange Format (ReqIF). In ArchiMate® 3.0, a statement is a Relationship.

## SpecIF:shows (SpecIF:TermStatementClass)
- dcterms:identifier: SC-shows
- SpecIF:Revision: 1.1
- dcterms:description: A [[SpecIF:Diagram]] 'shows' a model element, e.g, a [[FMC:Actor]], [[FMC:State]], [[FMC:Event]] or [[SpecIF:Collection]].
- SpecIF:LocalTerm: shows
- SpecIF:Origin: http://specif.de
- SpecIF:Domain: System Model Integration
- SpecIF:LifecycleStatus: SpecIF:LifecycleStatusReleased
- SpecIF:isUndirected: false
- SpecIF:Instantiation: auto

## SpecIF:contains (SpecIF:TermStatementClass)
- SpecIF:Revision: 1.2
- dcterms:description: General containment, such as:
  - Component-A contains Component-B
  - DataObject-1 contains Attribute-1.1
- SpecIF:LocalTerm: contains
- SpecIF:Origin: http://fmc-modeling.org/
- SpecIF:Domain: System Model Integration
- SpecIF:LifecycleStatus: SpecIF:LifecycleStatusReleased
- SpecIF:isUndirected: false
- SpecIF:Instantiation: auto

## ArchiMate:unites (SpecIF:TermStatementClass)
- SpecIF:Revision: 1.2
- dcterms:description: General containment. In ArchiMate, the uniting concept includes:
  - The *composition* relationship represents that an element consists of one or more other concepts.
  - The *aggregation* relationship represents that an element combines one or more other concepts.
  - The *assignment* relationship represents the allocation of responsibility, performance of behavior, storage, or execution.
  - The *realization* relationship represents that an entity plays a critical role in the creation, achievement, sustenance, or operation of a more abstract entity.

  The kind of uniting is specified in a property with title [[dcterms:type]].
- SpecIF:LocalTerm: unites
- SpecIF:Origin: https://pubs.opengroup.org/architecture/archimate3-doc/chap05.html
- SpecIF:Domain: System Model Integration
- SpecIF:LifecycleStatus: SpecIF:LifecycleStatusReleased
- SpecIF:isUndirected: false
- SpecIF:Instantiation: auto

## FMC:contains (SpecIF:TermStatementClass)
- SpecIF:Revision: 1.2
- dcterms:description: A [[FMC:Actor]] or [[FMC:State]] 'contains' a [[FMC:Actor]], [[FMC:State]] or [[FMC:Event]]. More concretely, Component-A contains Component-B.
- SpecIF:Origin: http://fmc-modeling.org/
- SpecIF:Domain: System Model Integration
- SpecIF:LifecycleStatus: SpecIF:LifecycleStatusReleased
- SpecIF:isUndirected: false
- SpecIF:Instantiation: auto

## SpecIF:satisfies (SpecIF:TermStatementClass)
- dcterms:description: A [[FMC:Actor]] or [[FMC:State]] 'satisfies' a [[IREB:Requirement]].
- SpecIF:LocalTerm: satisfies
- SpecIF:Origin: http://specif.de
- SpecIF:LifecycleStatus: SpecIF:LifecycleStatusEquivalent

## SpecIF:implements (SpecIF:TermStatementClass)
- dcterms:description: A [[FMC:Actor]] or [[FMC:State]] 'implements' a [[SpecIF:Feature]].
- SpecIF:LocalTerm: implements
- SpecIF:Origin: http://specif.de
- SpecIF:LifecycleStatus: SpecIF:LifecycleStatusReleased

## SpecIF:influences (SpecIF:TermStatementClass)
- dcterms:description: The influence relationship represents that an element affects the implementation or achievement of some motivation element.
- SpecIF:LocalTerm: influences
- SpecIF:Origin: https://pubs.opengroup.org/architecture/archimate3-doc/chap05.html
- SpecIF:Domain: System Model Integration
- SpecIF:LifecycleStatus: SpecIF:LifecycleStatusExperimental

## rdf:type (SpecIF:TermStatementClass)
- dcterms:description: A triple of the form: R rdf:type C states that C is an instance of rdfs:Class and R is an instance of C.
  The rdfs:domain of rdf:type is rdfs:Resource. The rdfs:range of rdf:type is rdfs:Class.
  This term is also used as a SpecIF propertyClass.
- SpecIF:Origin: https://www.w3.org/TR/rdf-schema/#ch_type
- SpecIF:Domain: System Model Integration
- SpecIF:LifecycleStatus: SpecIF:LifecycleStatusReleased
- SpecIF:isUndirected: false

## oslc_rm:satisfies (SpecIF:TermStatementClass)
- dcterms:description: The object is satisfied by the subject. (source: OSLC)
  SpecIF suggests that the subject is confined to a model element, e.g, a [[FMC:Actor]] or [[FMC:State]], and the object is confined to a [[IREB:Requirement]]. More concretely, an example for this type of statement is 'Component-X satisfies 'Requirement-4711'.
- SpecIF:LocalTerm: satisfies
- SpecIF:Origin: http://open-services.net/bin/view/Main/RmSpecificationV2
- SpecIF:LifecycleStatus: SpecIF:LifecycleStatusReleased
- SpecIF:isUndirected: false
- SpecIF:Instantiation: user

## oslc_rm:satisfiedBy (SpecIF:TermStatementClass)
- SpecIF:Revision: 1.2
- dcterms:description: The subject is satisfied by the object. For example, a user requirement is satisfied by a system requirement. (source: OSLC)
- SpecIF:LocalTerm: is satisfied by
- SpecIF:Origin: http://open-services.net/bin/view/Main/RmSpecificationV2
- SpecIF:Domain: Requirement Engineering, Automotive Stakeholder Request Clarification Process
- SpecIF:LifecycleStatus: SpecIF:LifecycleStatusReleased
- SpecIF:isUndirected: false
- SpecIF:Instantiation: user

## oslc_rm:elaborates (SpecIF:TermStatementClass)
- dcterms:description: The object is elaborated by the subject. For example, a use case elaborates a requirement.
- SpecIF:Origin: http://open-services.net/bin/view/Main/RmSpecificationV2
- SpecIF:LifecycleStatus: SpecIF:LifecycleStatusEquivalent
- SpecIF:isUndirected: false

## oslc_rm:elaboratedBy (SpecIF:TermStatementClass)
- dcterms:description: The subject is elaborated by the object.
- SpecIF:Origin: http://open-services.net/bin/view/Main/RmSpecificationV2

## oslc_rm:specifies (SpecIF:TermStatementClass)
- dcterms:description: The object is specified by the subject. For example, a requirement specifies a model element.
- SpecIF:Origin: http://open-services.net/bin/view/Main/RmSpecificationV2

## oslc_rm:specifiedBy (SpecIF:TermStatementClass)
- dcterms:description: The subject is specified by the object.
- SpecIF:Origin: http://open-services.net/bin/view/Main/RmSpecificationV2

## oslc_rm:affectedBy (SpecIF:TermStatementClass)
- dcterms:description: Requirement is affected by a resource, such as a defect or issue.
- SpecIF:Origin: http://open-services.net/bin/view/Main/RmSpecificationV2

## oslc_rm:trackedBy (SpecIF:TermStatementClass)
- dcterms:description: Resource, such as a change request, which tracks this requirement.
- SpecIF:Origin: http://open-services.net/bin/view/Main/RmSpecificationV2

## oslc_rm:implementedBy (SpecIF:TermStatementClass)
- dcterms:description: Resource, such as a change request, which implements this requirement.
- SpecIF:Origin: http://open-services.net/bin/view/Main/RmSpecificationV2

## oslc_rm:validatedBy (SpecIF:TermStatementClass)
- dcterms:description: Resource, such as a test case, which validates this requirement.
- SpecIF:Origin: http://open-services.net/bin/view/Main/RmSpecificationV2

## oslc_rm:decomposes (SpecIF:TermStatementClass)
- dcterms:description: The object is decomposed by the subject. For example, a collection of subsystems decomposes a system.
- SpecIF:Origin: http://open-services.net/bin/view/Main/RmSpecificationV2

## oslc_rm:decomposedBy (SpecIF:TermStatementClass)
- dcterms:description: The subject is decomposed by the object.
- SpecIF:Origin: http://open-services.net/bin/view/Main/RmSpecificationV2

## oslc_rm:constrains (SpecIF:TermStatementClass)
- dcterms:description: The object is constrained by the subject. For example, a safety requirement constrains a functional requirement.
- SpecIF:Origin: http://open-services.net/bin/view/Main/RmSpecificationV2

## oslc_rm:constrainedBy (SpecIF:TermStatementClass)
- dcterms:description: The subject is constrained by the object.
- SpecIF:Origin: http://open-services.net/bin/view/Main/RmSpecificationV2

## SpecIF:serves (SpecIF:TermStatementClass)
- SpecIF:Revision: 1.2
- dcterms:description: A [[FMC:Actor]] 'serves' a FMC:Actor.
- SpecIF:Origin: http://specif.de
- SpecIF:Domain: System Model Integration
- SpecIF:LifecycleStatus: SpecIF:LifecycleStatusReleased
- SpecIF:isUndirected: false
- SpecIF:Instantiation: auto

## SpecIF:reads (SpecIF:TermStatementClass)
- SpecIF:Revision: 1.2
- dcterms:description: A [[FMC:Actor]] 'reads' a [[FMC:State]].
- SpecIF:LocalTerm: reads
- SpecIF:Origin: http://specif.de
- SpecIF:Domain: System Model Integration
- SpecIF:LifecycleStatus: SpecIF:LifecycleStatusReleased
- SpecIF:isUndirected: false
- SpecIF:Instantiation: auto

## SpecIF:writes (SpecIF:TermStatementClass)
- SpecIF:Revision: 1.2
- dcterms:description: A [[FMC:Actor]] 'writes' (changes) a [[FMC:State]].
- SpecIF:LocalTerm: writes
- SpecIF:Origin: http://specif.de
- SpecIF:Domain: System Model Integration
- SpecIF:LifecycleStatus: SpecIF:LifecycleStatusReleased
- SpecIF:isUndirected: false
- SpecIF:Instantiation: auto

## SpecIF:stores (SpecIF:TermStatementClass)
- SpecIF:Revision: 1.2
- dcterms:description: A [[FMC:Actor]] 'stores' (writes and reads) a [[FMC:State]].
- SpecIF:Origin: http://specif.de
- SpecIF:Domain: System Model Integration
- SpecIF:LifecycleStatus: SpecIF:LifecycleStatusEquivalent
- SpecIF:isUndirected: false
- SpecIF:Instantiation: auto

## SpecIF:accesses (SpecIF:TermStatementClass)
- SpecIF:Revision: 1.2
- dcterms:description: A [[FMC:Actor]] 'accesses' (writes or reads) a [[FMC:State]].
- SpecIF:LocalTerm: accesses
- SpecIF:Origin: http://specif.de
- SpecIF:Domain: System Model Integration
- SpecIF:LifecycleStatus: SpecIF:LifecycleStatusReleased
- SpecIF:isUndirected: false
- SpecIF:Instantiation: auto

## FMC:modifies (SpecIF:TermStatementClass)
- dcterms:description: A [[FMC:Actor]] writes _and_ reads a [[FMC:State]].
- SpecIF:LocalTerm: modifies
- SpecIF:Origin: http://specif.de
- SpecIF:Domain: System Model Integration
- SpecIF:LifecycleStatus: SpecIF:LifecycleStatusEquivalent

## SpecIF:communicatesWith (SpecIF:TermStatementClass)
- SpecIF:Revision: 1.2
- dcterms:description: A [[FMC:Actor]] 'communicates' with a [[FMC:Actor]].
- SpecIF:LocalTerm: communicates with
- SpecIF:Origin: http://specif.de
- SpecIF:Domain: System Model Integration
- SpecIF:LifecycleStatus: SpecIF:LifecycleStatusReleased
- SpecIF:isUndirected: false
- SpecIF:Instantiation: auto

## SpecIF:sendsTo (SpecIF:TermStatementClass)
- SpecIF:Revision: 1.2
- dcterms:description: A [[FMC:Actor]] 'sends' a message to a [[FMC:Actor]].
- SpecIF:LocalTerm: sends to
- SpecIF:Origin: http://specif.de
- SpecIF:Domain: System Model Integration
- SpecIF:LifecycleStatus: SpecIF:LifecycleStatusReleased
- SpecIF:isUndirected: false
- SpecIF:Instantiation: auto

## SpecIF:receivesFrom (SpecIF:TermStatementClass)
- SpecIF:Revision: 1.2
- dcterms:description: A [[FMC:Actor]] 'receives' a message from a [[FMC:Actor]].
- SpecIF:LocalTerm: receives from
- SpecIF:Origin: http://specif.de
- SpecIF:Domain: System Model Integration
- SpecIF:LifecycleStatus: SpecIF:LifecycleStatusReleased
- SpecIF:isUndirected: false
- SpecIF:Instantiation: auto

## follows (SpecIF:TermStatementClass)
- SpecIF:Revision: 1.2
- dcterms:description: A [[FMC:Actor]] 'follows' a [[FMC:Actor]]; e.g. in a business process or activity flow.
- SpecIF:Origin: http://specif.de
- SpecIF:Domain: System Model Integration
- SpecIF:LifecycleStatus: SpecIF:LifecycleStatusReleased
- SpecIF:isUndirected: false
- SpecIF:Instantiation: auto

## SpecIFF:precedes (SpecIF:TermStatementClass)
- SpecIF:Revision: 1.2
- dcterms:description: A [[FMC:Actor]] 'precedes' a [[FMC:Actor]]; e.g. in a business process or activity flow.
- SpecIF:Origin: http://specif.de
- SpecIF:Domain: System Model Integration
- SpecIF:LifecycleStatus: SpecIF:LifecycleStatusReleased
- SpecIF:isUndirected: false
- SpecIF:Instantiation: auto

## SpecIF:signals (SpecIF:TermStatementClass)
- dcterms:description: A [[FMC:Actor]] 'signals' a [[FMC:Event]].
- SpecIF:Origin: http://specif.de
- SpecIF:Domain: System Model Integration
- SpecIF:LifecycleStatus: SpecIF:LifecycleStatusDeprecated

## SpecIF:triggers (SpecIF:TermStatementClass)
- dcterms:description: A [[FMC:Event]] 'triggers' a [[FMC:Actor]].
- SpecIF:Origin: http://specif.de
- SpecIF:Domain: System Model Integration
- SpecIF:LifecycleStatus: SpecIF:LifecycleStatusDeprecated

## SpecIF:dependsOn (SpecIF:TermStatementClass)
- SpecIF:Revision: 1.2
- dcterms:description: A [[IREB:Requirement]] 'depends on' another [[IREB:Requirement]].
- SpecIF:Origin: http://specif.de
- SpecIF:Domain: Requirement Engineering, Automotive Stakeholder Request Clarification Process, System Model Integration
- SpecIF:LifecycleStatus: SpecIF:LifecycleStatusReleased
- SpecIF:isUndirected: false
- SpecIF:Instantiation: user

## SysML:traces (SpecIF:TermStatementClass)
- SpecIF:Revision: 1.2
- dcterms:description: A [[IREB:Requirement]] traces another [[IREB:Requirement]].
- SpecIF:Origin: http://specif.de
- SpecIF:Domain: Requirement Engineering, Automotive Stakeholder Request Clarification Process, System Model Integration
- SpecIF:LifecycleStatus: SpecIF:LifecycleStatusReleased
- SpecIF:isUndirected: false
- SpecIF:Instantiation: user

## SysML:isDerivedFrom (SpecIF:TermStatementClass)
- SpecIF:Revision: 1.2
- dcterms:description: A [[IREB:Requirement]] isDerivedFrom another [[IREB:Requirement]].
- SpecIF:Origin: http://specif.de
- SpecIF:Domain: Requirement Engineering, Automotive Stakeholder Request Clarification Process, System Model Integration
- SpecIF:LifecycleStatus: SpecIF:LifecycleStatusReleased
- SpecIF:isUndirected: false
- SpecIF:Instantiation: user

## IREB:refines (SpecIF:TermStatementClass)
- SpecIF:Revision: 1.2
- dcterms:description: A [[IREB:Requirement]] refines another [[IREB:Requirement]].
- SpecIF:Origin: https://www.ireb.org/en/downloads/#cpre-glossary
- SpecIF:Domain: Requirement Engineering
- SpecIF:LifecycleStatus: SpecIF:LifecycleStatusReleased
- SpecIF:isUndirected: false
- SpecIF:Instantiation: user

## SpecIF:duplicates (SpecIF:TermStatementClass)
- SpecIF:Revision: 1.2
- dcterms:description: A [[IREB:Requirement]] 'duplicates' another [[IREB:Requirement]].
- SpecIF:Origin: http://specif.de
- SpecIF:Domain: Requirement Engineering
- SpecIF:LifecycleStatus: SpecIF:LifecycleStatusReleased
- SpecIF:isUndirected: true
- SpecIF:Instantiation: user

## SpecIF:contradicts (SpecIF:TermStatementClass)
- SpecIF:Revision: 1.2
- dcterms:description: A [[IREB:Requirement]] 'contradicts' another [[IREB:Requirement]].
- SpecIF:Origin: http://specif.de
- SpecIF:Domain: Requirement Engineering
- SpecIF:LifecycleStatus: SpecIF:LifecycleStatusReleased
- SpecIF:isUndirected: true
- SpecIF:Instantiation: user

## SysML:isAllocatedTo (SpecIF:TermStatementClass)
- SpecIF:Revision: 1.2
- dcterms:description: An [[FMC:Actor]] is allocated to another [[FMC:Actor]] (e.g. a logical function is allocated to a physical component.
- SpecIF:Origin: http://specif.de
- SpecIF:Domain: System Model Integration
- SpecIF:LifecycleStatus: SpecIF:LifecycleStatusReleased
- SpecIF:isUndirected: false
- SpecIF:Instantiation: auto

## SysML:isAssociatedWith (SpecIF:TermStatementClass)
- SpecIF:Revision: 1.2
- dcterms:description: A [[FMC:State]] is associated with another [[FMC:State]] (e.g. a class is associated with another class, as shown in a UML Class Diagram).
- SpecIF:Origin: http://specif.de
- SpecIF:Domain: System Model Integration
- SpecIF:LifecycleStatus: SpecIF:LifecycleStatusReleased
- SpecIF:isUndirected: false
- SpecIF:Instantiation: auto

## SysML:isComposedOf (SpecIF:TermStatementClass)
- SpecIF:Revision: 1.2
- dcterms:description: An [[FMC:Actor]] is composed of another [[FMC:Actor]].
- SpecIF:Origin: http://specif.de
- SpecIF:Domain: System Model Integration
- SpecIF:LifecycleStatus: SpecIF:LifecycleStatusExperimental
- SpecIF:isUndirected: false
- SpecIF:Instantiation: auto

## SysML:composes (SpecIF:TermStatementClass)
- SpecIF:Revision: 1.2
- dcterms:description: An [[FMC:Actor]] is composed of another [[FMC:Actor]].
- SpecIF:Origin: http://specif.de
- SpecIF:Domain: System Model Integration
- SpecIF:LifecycleStatus: SpecIF:LifecycleStatusReleased
- SpecIF:isUndirected: false
- SpecIF:Instantiation: auto

## SysML:isAggregatedBy (SpecIF:TermStatementClass)
- SpecIF:Revision: 1.2
- dcterms:description: An [[FMC:Actor]] is aggregated by another [[FMC:Actor]].
- SpecIF:Origin: http://specif.de
- SpecIF:Domain: System Model Integration
- SpecIF:LifecycleStatus: SpecIF:LifecycleStatusExperimental
- SpecIF:isUndirected: false
- SpecIF:Instantiation: auto

## SysML:aggregates (SpecIF:TermStatementClass)
- SpecIF:Revision: 1.2
- dcterms:description: An [[FMC:Actor]] aggregates another [[FMC:Actor]].
- SpecIF:Origin: http://specif.de
- SpecIF:Domain: System Model Integration
- SpecIF:LifecycleStatus: SpecIF:LifecycleStatusReleased
- SpecIF:isUndirected: false
- SpecIF:Instantiation: auto

## SysML:uses (SpecIF:TermStatementClass)
- SpecIF:Revision: 1.2
- SpecIF:Origin: http://specif.de
- SpecIF:Domain: System Model Integration
- SpecIF:LifecycleStatus: SpecIF:LifecycleStatusReleased
- SpecIF:isUndirected: false
- SpecIF:Instantiation: auto

## SysML:extends (SpecIF:TermStatementClass)
- SpecIF:Revision: 1.2
- dcterms:description: An [[FMC:Actor]] «UseCase» extends another [[FMC:Actor]] «UseCase».
- SpecIF:Origin: http://specif.de
- SpecIF:Domain: System Model Integration
- SpecIF:LifecycleStatus: SpecIF:LifecycleStatusReleased
- SpecIF:isUndirected: false
- SpecIF:Instantiation: auto

## SysML:includes (SpecIF:TermStatementClass)
- SpecIF:Revision: 1.2
- dcterms:description: An [[FMC:Actor]] «UseCase» includes another [[FMC:Actor]] «UseCase».
- SpecIF:Origin: http://specif.de
- SpecIF:Domain: System Model Integration
- SpecIF:LifecycleStatus: SpecIF:LifecycleStatusReleased
- SpecIF:isUndirected: false
- SpecIF:Instantiation: auto

## SysML:isSpecializationOf (SpecIF:TermStatementClass)
- SpecIF:Revision: 1.2
- dcterms:description: An [[FMC:Actor]] is a specialization of another [[FMC:Actor]]; similarly for [[FMC:State]] and [[FMC:Event]].
- SpecIF:Origin: http://specif.de
- SpecIF:Domain: System Model Integration
- SpecIF:LifecycleStatus: SpecIF:LifecycleStatusReleased
- SpecIF:isUndirected: false
- SpecIF:Instantiation: auto

## SysML:isSpecialisationOf (SpecIF:TermStatementClass)
- dcterms:description: An FMC:Actor is a specialization of another FMC:Actor; similarly for FMC:State and FMC:Event.
- SpecIF:Origin: http://specif.de
- SpecIF:Domain: System Model Integration
- SpecIF:LifecycleStatus: SpecIF:LifecycleStatusDeprecated

## SysML:isGeneralizationOf (SpecIF:TermStatementClass)
- SpecIF:Revision: 1.2
- dcterms:description: An [[FMC:Actor]] is a generalization of another [[FMC:Actor]]; similarly for [[FMC:State]] and [[FMC:Event]].
- SpecIF:Origin: http://specif.de
- SpecIF:Domain: System Model Integration
- SpecIF:LifecycleStatus: SpecIF:LifecycleStatusReleased
- SpecIF:isUndirected: false
- SpecIF:Instantiation: auto

## SysML:isGeneralisationOf (SpecIF:TermStatementClass)
- dcterms:description: An FMC:Actor is a generalization of another FMC:Actor; similarly for FMC:State and FMC:Event.
- SpecIF:Origin: http://specif.de
- SpecIF:Domain: System Model Integration
- SpecIF:LifecycleStatus: SpecIF:LifecycleStatusDeprecated

## SpecIF:inheritsFrom (SpecIF:TermStatementClass)
- dcterms:description: A model-element class inherits from another. For example a data-object of class [[FMC:State]] inherits from another data-object, as shown in a UML Class Diagram).
- SpecIF:Origin: http://specif.de
- SpecIF:LifecycleStatus: SpecIF:LifecycleStatusExperimental

## SpecIF:hasEnumValue (SpecIF:TermStatementClass)
- dcterms:description: A property has an enumerated value.
- SpecIF:Origin: http://specif.de
- SpecIF:Domain: Ontology
- SpecIF:LifecycleStatus: SpecIF:LifecycleStatusSubmitted

## SpecIF:isEligibleAsSubject (SpecIF:TermStatementClass)
- dcterms:description: A resource-term or statement-term is eligible as a subject of a predicate-term.

  Or concretely: A resource or statement of this class is eligible as the predicate's subject.
- SpecIF:Origin: http://specif.de
- SpecIF:Domain: Ontology
- SpecIF:LifecycleStatus: SpecIF:LifecycleStatusSubmitted

## SpecIF:isEligibleAsObject (SpecIF:TermStatementClass)
- dcterms:description: A resource-term or statement-term is eligible as an object of a predicate-term.

  Or concretely: A resource or statement of this class is eligible as the predicate's object.
- SpecIF:Origin: http://specif.de
- SpecIF:Domain: Ontology
- SpecIF:LifecycleStatus: SpecIF:LifecycleStatusSubmitted

## SpecIF:refersTo (SpecIF:TermStatementClass)
- dcterms:identifier: SC-refersTo
- SpecIF:Revision: 1.2
- dcterms:description: A resource 'refers to' any other resource.
- SpecIF:Origin: http://specif.de
- SpecIF:LifecycleStatus: SpecIF:LifecycleStatusReleased
- SpecIF:isUndirected: false

## SpecIF:commentRefersTo (SpecIF:TermStatementClass)
- SpecIF:Revision: 1.2
- dcterms:description: A [[SpecIF:Comment]] 'refers to' any other resource.
- SpecIF:Origin: http://specif.de
- SpecIF:Domain: Base
- SpecIF:LifecycleStatus: SpecIF:LifecycleStatusReleased
- SpecIF:isUndirected: false
- SpecIF:Instantiation: auto

## SpecIF:mentions (SpecIF:TermStatementClass)
- dcterms:description: A resource's text refers to another resorce (e.g. by hyper-link).
- SpecIF:Origin: http://specif.de
- SpecIF:LifecycleStatus: SpecIF:LifecycleStatusReleased

## SpecIF:isSynonymOf (SpecIF:TermStatementClass)
- SpecIF:Revision: 1.2
- dcterms:description: A term is synonymous with another term, if both represent the same concept.
  According to Wikipedia, "a synonym is a word or phrase that means exactly or nearly the same as another word or phrase in the same language. Words that are synonyms are said to be synonymous".
- SpecIF:Origin: http://specif.de
- SpecIF:Domain: Ontology
- SpecIF:LifecycleStatus: SpecIF:LifecycleStatusReleased
- SpecIF:isUndirected: false
- SpecIF:Instantiation: user

## SpecIF:isInverseOf (SpecIF:TermStatementClass)
- dcterms:description: A term is the inverse of another term.
  For example, a system 'B' contains a component '11', thus '11' isContainedBy 'B'.
- SpecIF:Origin: http://specif.de
- SpecIF:LifecycleStatus: SpecIF:LifecycleStatusDeprecated

## SpecIF:isAntonymOf (SpecIF:TermStatementClass)
- SpecIF:Revision: 1.2
- dcterms:description: According to Wikipedia, "the term antonym (and the related antonymy) is commonly taken to be synonymous with opposite, but antonym also has other more restricted meanings. Graded (or gradable) antonyms are word pairs whose meanings are opposite and which lie on a continuous spectrum (_hot_, _cold_). Complementary antonyms are word pairs whose meanings are opposite but whose meanings do not lie on a continuous spectrum (_push_, _pull_). Relational antonyms are word pairs where opposite makes sense only in the context of the relationship between the two meanings (_teacher_, _pupil_)".
- SpecIF:Origin: https://en.wikipedia.org/wiki/Opposite_(semantics)
- SpecIF:Domain: Ontology
- SpecIF:LifecycleStatus: SpecIF:LifecycleStatusReleased
- SpecIF:isUndirected: false
- SpecIF:Instantiation: user

## owl:sameAs (SpecIF:TermStatementClass)
- SpecIF:Revision: 1.2
- dcterms:description: An owl:sameAs statement indicates that two URI references actually refer to the same thing: the individuals have the same "identity". (source: OWL)
- SpecIF:Origin: https://www.w3.org/TR/owl-ref
- SpecIF:Domain: System Model Integration
- SpecIF:LifecycleStatus: SpecIF:LifecycleStatusReleased
- SpecIF:isUndirected: true
- SpecIF:Instantiation: user

## SpecIF:sameAs (SpecIF:TermStatementClass)
- dcterms:description: A resource represents the same entity as another resource.
- SpecIF:Origin: http://specif.de
- SpecIF:LifecycleStatus: SpecIF:LifecycleStatusEquivalent
- SpecIF:isUndirected: true

## Property Class Terms (SpecIF:Heading)
- dcterms:description: A property carries information 'payload' and may be applied to resources or statements. The SpecIF terms listed in this chapter are used as property name/title, whereas the information is provided as 'value'. Usually a combination of complimentary properties is used per resource or statement class.
  A property corresponds to an 'ATTRIBUTE-DEFINITION' resp. 'ATTRIBUTE-VALUE' in the Requirements Interchange Format (ReqIF).

## dcterms:identifier (SpecIF:TermPropertyClassString)
- dcterms:identifier: PC-VisibleId
- SpecIF:Revision: 1.1
- dcterms:description: A unique reference to the resource within a given context. (source: DCMI)
  An identifier for a resource. This identifier may be unique with a scope that is defined by the RM provider. Assigned by the service provider when a resource is created. Not intended for end-user display. (source: OSLC)
- SpecIF:Origin: http://dublincore.org/specifications/
- SpecIF:LifecycleStatus: SpecIF:LifecycleStatusReleased
- SpecIF:multiple: false
- SpecIF:TextFormat: plain

## ReqIF.ForeignID (SpecIF:TermPropertyClassString)
- SpecIF:Revision: 1.2
- SpecIF:LocalTerm: Original ID
- SpecIF:Origin: https://www.prostep.org/fileadmin/downloads/prostep-ivip_ImplementationGuide_ReqIF_V1-8.pdf
- SpecIF:Domain: Automotive Stakeholder Request Clarification Process
- SpecIF:LifecycleStatus: SpecIF:LifecycleStatusEquivalent
- SpecIF:multiple: false
- SpecIF:TextFormat: plain

## dcterms:title (SpecIF:TermPropertyClassString)
- dcterms:identifier: PC-Name
- SpecIF:Revision: 1.1
- SpecIF:LocalTerm: Name
- dcterms:description: A name given to the resource. (source: DCMI)
  Title (reference: Dublin Core) of the resource represented as rich text in XHTML content. SHOULD include only content that is valid inside an XHTML 'span' element. (source: OSLC)
- SpecIF:Origin: http://dublincore.org/specifications/
- SpecIF:Domain: Base
- SpecIF:LifecycleStatus: SpecIF:LifecycleStatusReleased
- SpecIF:multiple: false
- SpecIF:multiLanguage: true
- SpecIF:TextFormat: plain
- SpecIF:StringMaxLength: 256

## ReqIF.Name (SpecIF:TermPropertyClassString)
- SpecIF:Revision: 1.2
- SpecIF:LocalTerm: Name
- SpecIF:Origin: https://www.prostep.org/fileadmin/downloads/prostep-ivip_ImplementationGuide_ReqIF_V1-8.pdf
- SpecIF:Domain: Base, Automotive Stakeholder Request Clarification Process
- SpecIF:LifecycleStatus: SpecIF:LifecycleStatusEquivalent
- SpecIF:multiple: false
- SpecIF:multiLanguage: true
- SpecIF:TextFormat: xhtml
- SpecIF:StringMaxLength: 256

## dcterms:description (SpecIF:TermPropertyClassString)
- dcterms:identifier: PC-Description
- SpecIF:Revision: 1.1
- dcterms:description: An account of the resource. (source: DCMI)
  Descriptive text (reference: Dublin Core) about resource represented as rich text in XHTML content. SHOULD include only content that is valid and suitable inside an XHTML 'div' element. (source: OSLC)
- SpecIF:LocalTerm: Description
- SpecIF:Origin: http://dublincore.org/specifications/
- SpecIF:Domain: Base
- SpecIF:LifecycleStatus: SpecIF:LifecycleStatusReleased
- SpecIF:multiple: false
- SpecIF:multiLanguage: true
- SpecIF:TextFormat: xhtml

## ReqIF.Text (SpecIF:TermPropertyClassString)
- SpecIF:Revision: 1.2
- SpecIF:LocalTerm: Description
- SpecIF:Origin: https://www.prostep.org/fileadmin/downloads/prostep-ivip_ImplementationGuide_ReqIF_V1-8.pdf
- SpecIF:Domain: Automotive Stakeholder Request Clarification Process
- SpecIF:LifecycleStatus: SpecIF:LifecycleStatusEquivalent
- SpecIF:multiple: false
- SpecIF:multiLanguage: true
- SpecIF:TextFormat: xhtml

## dcterms:type (SpecIF:TermPropertyClassString)
- dcterms:identifier: PC-Type
- SpecIF:Revision: 1.1
- dcterms:description: The nature or genre of the resource. (source: DCMI)
  Recommended best practice is to use a controlled vocabulary such as the DCMI Type Vocabulary [DCMITYPE]. To describe the file format, physical medium, or dimensions of the resource, use the Format element.
  For example, a [[FMC:Actor]] may represent a System Function, a System Component or a User Role. Similarly, in the context of process modelling, a FMC:Actor may represent a Process Step or again a User Role. So, all of these are meaningful values for a FMC:Actor's property named dcterms:type.
- SpecIF:LocalTerm: Element Type
- SpecIF:Origin: http://dublincore.org/specifications/
- SpecIF:Domain: Base
- SpecIF:LifecycleStatus: SpecIF:LifecycleStatusReleased
- SpecIF:multiple: false
- SpecIF:TextFormat: plain
- SpecIF:StringMaxLength: 256

## SpecIF:Type (SpecIF:TermPropertyClassString)
- SpecIF:Origin: http://specif.de
- SpecIF:LifecycleStatus: SpecIF:LifecycleStatusReleased

## ReqIF.Category (SpecIF:TermPropertyClassString)
- SpecIF:Revision: 1.2
- SpecIF:LocalTerm: Category
- SpecIF:Origin: https://www.prostep.org/fileadmin/downloads/prostep-ivip_ImplementationGuide_ReqIF_V1-8.pdf
- SpecIF:Domain: System Model Integration
- SpecIF:LifecycleStatus: SpecIF:LifecycleStatusEquivalent
- SpecIF:multiple: false
- SpecIF:TextFormat: plain
- SpecIF:StringMaxLength: 256

## SpecIF:Diagram (SpecIF:TermPropertyClassString)
- dcterms:identifier: PC-Diagram
- SpecIF:Revision: 1.1
- dcterms:description: One or more diagrams illustrating the resource.
- SpecIF:Origin: http://specif.de
- SpecIF:Domain: Base, Requirement Engineering, Automotive Stakeholder Request Clarification Process, System Model Integration
- SpecIF:LifecycleStatus: SpecIF:LifecycleStatusReleased
- SpecIF:multiple: true
- SpecIF:TextFormat: xhtml

## SpecIF:Notation (SpecIF:TermPropertyClassString)
- dcterms:identifier: PC-Notation
- SpecIF:Revision: 1.2
- dcterms:description: The notation used by a model diagram, e.g. 'BPMN 2.0', 'SysML Activity Diagram' or 'FMC Block Diagram'.
- SpecIF:Origin: http://specif.de
- SpecIF:Domain: System Model Integration
- SpecIF:LifecycleStatus: SpecIF:LifecycleStatusReleased
- SpecIF:multiple: false
- SpecIF:TextFormat: plain
- SpecIF:StringMaxLength: 32

## SpecIF:Category (SpecIF:TermPropertyClassString)
- dcterms:description: The 'Category' (class) of the resource, usually with an enumerated value.
  Useful categories for requirements have been defined by the IREB, namely 'Function', 'Quality' and 'Constraint'.
- SpecIF:Origin: http://specif.de
- SpecIF:LifecycleStatus: SpecIF:LifecycleStatusReleased

## rdf:type (SpecIF:TermPropertyClassString)
- dcterms:description: rdf:type is an instance of rdf:Property that is used to state that a resource is an instance of a class.
  The rdfs:domain of rdf:type is rdfs:Resource. The rdfs:range of rdf:type is rdfs:Class.
  This term is also used as a SpecIF statementClass.
- SpecIF:Origin: https://www.w3.org/TR/rdf-schema/#ch_type
- SpecIF:LifecycleStatus: SpecIF:LifecycleStatusReleased
- SpecIF:multiple: false

## SpecIF:Id (SpecIF:TermPropertyClassString)
- dcterms:description: A unique reference to the resource within a given context.
- SpecIF:Origin: http://specif.de
- SpecIF:LifecycleStatus: SpecIF:LifecycleStatusDeprecated

## dcterms:subject (SpecIF:TermPropertyClassString)
- dcterms:description: The topic of the resource. (source: DCMI)
  Tag or keyword for a resource. Each occurrence of a dcterms:subject property denotes an additional tag for the resource. (source: OSLC)
- SpecIF:Origin: http://dublincore.org/specifications/
- SpecIF:LifecycleStatus: SpecIF:LifecycleStatusReleased

## dcterms:creator (SpecIF:TermPropertyClassString)
- dcterms:description: An entity primarily responsible for making the resource. (source: DCMI)
  Creator(s) of resource (reference: Dublin Core). It is likely that the target resource will be a [[foaf:Person]] but that is not necessarily the case. (source: OSLC)
- SpecIF:Origin: http://dublincore.org/specifications/
- SpecIF:LifecycleStatus: SpecIF:LifecycleStatusEquivalent

## SpecIF:createdBy (SpecIF:TermPropertyClassString)
- dcterms:description: A resource primarily responsible for making the resource.
- SpecIF:Origin: http://specif.de
- SpecIF:LifecycleStatus: SpecIF:LifecycleStatusReleased

## dcterms:created (SpecIF:TermPropertyClassTimestamp)
- dcterms:description: Timestamp of resource creation. (source: DCMI)
- SpecIF:Origin: http://dublincore.org/specifications/
- SpecIF:LifecycleStatus: SpecIF:LifecycleStatusEquivalent

## SpecIF:createdAt (SpecIF:TermPropertyClassTimestamp)
- dcterms:description: Date/time of creation of the resource.
- SpecIF:Origin: http://specif.de
- SpecIF:LifecycleStatus: SpecIF:LifecycleStatusReleased

## SpecIF:changedBy (SpecIF:TermPropertyClassString)
- dcterms:description: The author who made the last modification.
- SpecIF:Origin: http://specif.de
- SpecIF:LifecycleStatus: SpecIF:LifecycleStatusReleased

## dcterms:modified (SpecIF:TermPropertyClassTimestamp)
- dcterms:description: Timestamp last latest resource modification. (source: DCMI)
- SpecIF:Origin: http://dublincore.org/specifications/
- SpecIF:LifecycleStatus: SpecIF:LifecycleStatusEquivalent

## SpecIF:changedAt (SpecIF:TermPropertyClassTimestamp)
- dcterms:description: Date/time on which the resource was changed last.
- SpecIF:Origin: http://specif.de
- SpecIF:LifecycleStatus: SpecIF:LifecycleStatusReleased

## dcterms:contributor (SpecIF:TermPropertyClassString)
- dcterms:description: A resource responsible for making contributions to the resource. (source: DCMI)
- SpecIF:Origin: http://dublincore.org/specifications/
- SpecIF:LifecycleStatus: SpecIF:LifecycleStatusReleased

## dcterms:rightsHolder (SpecIF:TermPropertyClassString)
- dcterms:description: A person or organization owning or managing rights over the resource. (source: DCMI)
- SpecIF:Origin: http://dublincore.org/specifications/
- SpecIF:LifecycleStatus: SpecIF:LifecycleStatusReleased

## dcterms:rights (SpecIF:TermPropertyClassString)
- dcterms:description: Information about rights held in and over the resource. (source: DCMI)
- SpecIF:Origin: http://dublincore.org/specifications/
- SpecIF:LifecycleStatus: SpecIF:LifecycleStatusReleased

## oslc:shortTitle (SpecIF:TermPropertyClassString)
- dcterms:description: Short name identifying a resource, often used as an abbreviated identifier for presentation to end-users. SHOULD include only content that is valid inside an XHTML 'span' element.
- SpecIF:Origin: http://open-services.net/bin/view/Main/RmSpecificationV2

## oslc:serviceProvider (SpecIF:TermPropertyClassString)
- dcterms:description: The scope of a resource is a URI for the resource's OSLC Service Provider.
- SpecIF:Origin: http://open-services.net/bin/view/Main/RmSpecificationV2

## oslc:instanceShape (SpecIF:TermPropertyClassString)
- dcterms:description: Resource Shape that provides hints as to resource property value-types and allowed values.
- SpecIF:Origin: http://open-services.net/bin/view/Main/RmSpecificationV2

## SpecIF:Stereotype (SpecIF:TermPropertyClassString)
- dcterms:description: Describes the role or sub-type of a model-element. For example, a [[FMC:Actor]] may represent a System Function, a System Component or a User Role. Similarly, in the context of process modelling, a FMC:Actor may represent a Process Step or again a User Role. So, all of these are meaningful values for a FMC:Actor's property named SpecIF:Stereotype.
- SpecIF:Origin: http://specif.de
- SpecIF:LifecycleStatus: SpecIF:LifecycleStatusDeprecated

## UML:Stereotype (SpecIF:TermPropertyClassString)
- dcterms:description: Describes the role or sub-type of a model-element. For example, a [[FMC:Actor]] may represent a System Function, a System Component or a User Role. Similarly, in the context of process modelling, a FMC:Actor may represent a Process Step or again a User Role. So, all of these are meaningful values for a FMC:Actor's property named UML:Stereotype.
- SpecIF:Origin: http://specif.de
- SpecIF:LifecycleStatus: SpecIF:LifecycleStatusReleased

## IREB:RequirementType (SpecIF:TermPropertyClassString)
- dcterms:identifier: PC-RequirementType
- SpecIF:Revision: 1.2
- dcterms:description: Requirements are typically sub-classified into functional requirements ([[IREB:FunctionalRequirement]]), quality requirements ([[IREB:QualityRequirement]]) and constraints ([[IREB:Constraint]]). The latter two are also called non-functional requirements.
- SpecIF:Origin: https://www.ireb.org/en/downloads/#cpre-glossary
- SpecIF:LifecycleStatus: SpecIF:LifecycleStatusExperimental
- SpecIF:multiple: false
- SpecIF:TextFormat: plain
- SpecIF:StringMaxLength: 32

## SpecIF:SubClass (SpecIF:TermPropertyClassString)
- dcterms:description: Describes the role or sub-type of a model-element. For example, a [[FMC:Actor]] may represent a System Function, a System Component or a User Role. Similarly, in the context of process modelling, a FMC:Actor may represent a Process Step or again a User Role. So, all of these are meaningful values for a FMC:Actor's property named SpecIF:SubClass.
- SpecIF:Origin: http://specif.de
- SpecIF:LifecycleStatus: SpecIF:LifecycleStatusDeprecated

## SpecIF:LifecycleStatus (SpecIF:TermPropertyClassString)
- dcterms:identifier: PC-LifecycleStatus
- SpecIF:Revision: 1.2
- dcterms:description: The 'Lifecycle Status' of the resource.
- SpecIF:Origin: http://specif.de
- SpecIF:Domain: Base, Requirement Engineering, Automotive Stakeholder Request Clarification Process, System Model Integration, Ontology
- SpecIF:LifecycleStatus: SpecIF:LifecycleStatusReleased
- SpecIF:multiple: false
- SpecIF:TextFormat: plain
- SpecIF:StringMaxLength: 32

## ReqIF.ForeignState (SpecIF:TermPropertyClassString)
- SpecIF:Revision: 1.2
- SpecIF:LocalTerm: Original Status
- dcterms:description: The 'Lifecycle Status' of the resource.
- SpecIF:Origin: https://www.prostep.org/fileadmin/downloads/prostep-ivip_ImplementationGuide_ReqIF_V1-8.pdf
- SpecIF:Domain: Automotive Stakeholder Request Clarification Process
- SpecIF:LifecycleStatus: SpecIF:LifecycleStatusEquivalent
- SpecIF:multiple: false
- SpecIF:TextFormat: plain
- SpecIF:StringMaxLength: 32

## SpecIF:LocalTerm (SpecIF:TermPropertyClassString)
- SpecIF:Revision: 1.2
- SpecIF:LocalTerm: Local Term
- SpecIF:Origin: https://specif.de
- SpecIF:Domain: Ontology
- SpecIF:LifecycleStatus: SpecIF:LifecycleStatusReleased
- SpecIF:multiple: false
- SpecIF:multiLanguage: true
- SpecIF:TextFormat: plain
- SpecIF:StringMaxLength: 32

## SpecIF:LocalTermPlural (SpecIF:TermPropertyClassString)
- SpecIF:Revision: 1.2
- SpecIF:Origin: https://specif.de
- SpecIF:Domain: Ontology
- SpecIF:LifecycleStatus: SpecIF:LifecycleStatusReleased
- SpecIF:LocalTerm: Local Term (Plural)
- SpecIF:multiple: false
- SpecIF:multiLanguage: true
- SpecIF:TextFormat: plain
- SpecIF:StringMaxLength: 32

## SpecIF:Probability (SpecIF:TermPropertyClassReal)
- SpecIF:Origin: http://specif.de
- SpecIF:LifecycleStatus: SpecIF:LifecycleStatusReleased
- SpecIF:multiple: false
- SpecIF:RealMinInclusive: 0
- SpecIF:RealMaxInclusive: 1.1
- SpecIF:RealFractionDigits: 2

## SpecIF:Priority (SpecIF:TermPropertyClassString)
- dcterms:identifier: PC-Priority
- SpecIF:Revision: 1.2
- SpecIF:LocalTerm: Priority
- dcterms:description: Enumerated values for the 'Priority' of the resource.
- SpecIF:Origin: http://specif.de
- SpecIF:Domain: Requirement Engineering, Automotive Stakeholder Request Clarification Process, System Model Integration
- SpecIF:LifecycleStatus: SpecIF:LifecycleStatusReleased
- SpecIF:multiple: false
- SpecIF:TextFormat: plain
- SpecIF:StringMaxLength: 32

## SpecIF:EngineeringDiscipline (SpecIF:TermPropertyClassString)
- dcterms:identifier: PC-Discipline
- SpecIF:Revision: 1.2
- dcterms:description: Enumerated values for the 'Engineering Discipline' addressed by the term.
- SpecIF:Origin: http://specif.de
- SpecIF:Domain: Requirement Engineering, Automotive Stakeholder Request Clarification Process, System Model Integration
- SpecIF:LifecycleStatus: SpecIF:LifecycleStatusReleased
- SpecIF:multiple: true
- SpecIF:TextFormat: plain
- SpecIF:StringMaxLength: 32

## SpecIF:StakeholderGroup (SpecIF:TermPropertyClassString)
- SpecIF:Revision: 1.2
- dcterms:description: Enumerated values for the 'Stakehoder Group' addressed by the term.
- SpecIF:Origin: http://specif.de
- SpecIF:Domain: Requirement Engineering, Automotive Stakeholder Request Clarification Process, System Model Integration
- SpecIF:LifecycleStatus: SpecIF:LifecycleStatusReleased
- SpecIF:multiple: false
- SpecIF:TextFormat: plain
- SpecIF:StringMaxLength: 32

## SpecIF:Perspective (SpecIF:TermPropertyClassString)
- dcterms:identifier: PC-Perspective
- SpecIF:Revision: 1.2
- dcterms:description: Enumerated values for the perspective (of a requirement).
- SpecIF:Origin: http://specif.de
- SpecIF:Domain: Requirement Engineering, Automotive Stakeholder Request Clarification Process, System Model Integration
- SpecIF:LifecycleStatus: SpecIF:LifecycleStatusDeprecated
- SpecIF:multiple: false
- SpecIF:TextFormat: plain
- SpecIF:StringMaxLength: 32

## SpecIF:Responsible (SpecIF:TermPropertyClassString)
- dcterms:description: The 'Person' being responsible for the resource.
- SpecIF:Origin: http://specif.de
- SpecIF:LifecycleStatus: SpecIF:LifecycleStatusReleased

## SpecIF:Milestone (SpecIF:TermPropertyClassTimestamp)
- dcterms:description: A target 'Milestone' to implement the resource.
- SpecIF:Origin: http://specif.de
- SpecIF:LifecycleStatus: SpecIF:LifecycleStatusReleased

## SpecIF:DueDate (SpecIF:TermPropertyClassTimestamp)
- dcterms:description: A 'Due Date' for the resource.
- SpecIF:Origin: http://specif.de
- SpecIF:LifecycleStatus: SpecIF:LifecycleStatusReleased

## SpecIF:Benefit (SpecIF:TermPropertyClassString)
- SpecIF:Origin: http://specif.de
- SpecIF:LifecycleStatus: SpecIF:LifecycleStatusReleased

## SpecIF:Damage (SpecIF:TermPropertyClassString)
- SpecIF:Origin: http://specif.de
- SpecIF:LifecycleStatus: SpecIF:LifecycleStatusReleased

## SpecIF:Icon (SpecIF:TermPropertyClassString)
- dcterms:description: An icon associated with the resource class.
- SpecIF:Origin: http://specif.de
- SpecIF:LifecycleStatus: SpecIF:LifecycleStatusReleased

## SpecIF:Tag (SpecIF:TermPropertyClassString)
- SpecIF:Origin: http://specif.de
- SpecIF:LifecycleStatus: SpecIF:LifecycleStatusReleased

## SpecIF:Instantiation (SpecIF:TermPropertyClassString)
- dcterms:description: "user": a user creates, updates and deletes a resource's instance manually.
  "auto": a resource's instance is created, updated or deleted by an algorithm.
- SpecIF:Origin: http://specif.de
- SpecIF:LifecycleStatus: SpecIF:LifecycleStatusReleased

## SpecIF:Creation (SpecIF:TermPropertyClassString)
- dcterms:description: "manual": user interface supports creation, update and deletion of the resource.
  "auto": the resource is created, updated or deleted by an algorithm.
- SpecIF:Origin: http://specif.de
- SpecIF:LifecycleStatus: SpecIF:LifecycleStatusDeprecated

## SpecIF:Origin (SpecIF:TermPropertyClassString)
- dcterms:description: The origin (source, reference) of an information or requirement
- SpecIF:Origin: http://specif.de
- SpecIF:LifecycleStatus: SpecIF:LifecycleStatusReleased

## SpecIF:Subject (SpecIF:TermPropertyClassString)
- dcterms:description: The subject of a subject-predicate-object statement. Corresponds to a 'source' in ReqIF terminology.
- SpecIF:Origin: http://specif.de
- SpecIF:LifecycleStatus: SpecIF:LifecycleStatusReleased

## SpecIF:Source (SpecIF:TermPropertyClassString)
- dcterms:description: The subject of a subject-predicate-object statement.
- SpecIF:Origin: http://specif.de
- SpecIF:LifecycleStatus: SpecIF:LifecycleStatusDeprecated

## SpecIF:Object (SpecIF:TermPropertyClassString)
- dcterms:description: The object of a subject-predicate-object statement. Corresponds to a 'target' in ReqIF terminology.
- SpecIF:Origin: http://specif.de
- SpecIF:LifecycleStatus: SpecIF:LifecycleStatusReleased

## SpecIF:Target (SpecIF:TermPropertyClassString)
- dcterms:description: The object of a subject-predicate-object statement.
- SpecIF:Origin: http://specif.de
- SpecIF:LifecycleStatus: SpecIF:LifecycleStatusDeprecated

## SpecIF:FitCriteria (SpecIF:TermPropertyClassString)
- SpecIF:Origin: http://specif.de
- SpecIF:LifecycleStatus: SpecIF:LifecycleStatusReleased

## SpecIF:OrdinalMark (SpecIF:TermPropertyClassString)
- dcterms:description: A string to determine the ordering of elements. Rules:
  - For ordering, only alphanumeric characters are permissible. A letter case has no effect; for example, 'F' is equivalent to 'f'.
  - The ordering at character level is alphanumeric, i.e. '1' < '7' < 'D' < 'X'.
  - Single character substrings < two-character substrings < substrings with more characters, thus '9' < '12' < '114'.
  - The ordinal mark may be separated by non-alphanumeric characters. All separators are equivalent; e.g. '-' is equivalent to ';' or '/'.
  - Each alphanumeric substring is used for ordering on its hierarchical level; the leftmost substring is most significant for the overall ordering.
  - For example '1' < '1.2' < '1.Y' < '1.1a' < '1-1b' < '1-1C' < '2'.
  A regular expression for extracting the substrings of an ordinal mark is /([0-9a-z]+)[^0-9a-z]{0,1}/gi.
- SpecIF:Origin: http://specif.de
- SpecIF:LifecycleStatus: SpecIF:LifecycleStatusExperimental

## ReqIF-WF.CustomerStatus (SpecIF:TermPropertyClassString)
- dcterms:identifier: PC-CustomerStatus
- SpecIF:Revision: 1.2
- SpecIF:Origin: https://www.prostep.org/fileadmin/downloads/Recommendation_ReqIF_V2_RZ3.pdf
- SpecIF:Domain: Automotive Stakeholder Request Clarification Process
- SpecIF:LifecycleStatus: SpecIF:LifecycleStatusReleased
- SpecIF:multiple: false
- SpecIF:TextFormat: plain
- SpecIF:StringMaxLength: 32

## ReqIF-WF.CustomerComment (SpecIF:TermPropertyClassString)
- dcterms:identifier: PC-CustomerComment
- SpecIF:Revision: 1.2
- SpecIF:Origin: https://www.prostep.org/fileadmin/downloads/Recommendation_ReqIF_V2_RZ3.pdf
- SpecIF:Domain: Automotive Stakeholder Request Clarification Process
- SpecIF:LifecycleStatus: SpecIF:LifecycleStatusSubmitted
- SpecIF:multiple: true
- SpecIF:TextFormat: xhtml

## ReqIF-WF.SupplierStatus (SpecIF:TermPropertyClassString)
- dcterms:identifier: PC-SupplierStatus
- SpecIF:Revision: 1.2
- SpecIF:Origin: https://www.prostep.org/fileadmin/downloads/Recommendation_ReqIF_V2_RZ3.pdf
- SpecIF:Domain: Automotive Stakeholder Request Clarification Process
- SpecIF:LifecycleStatus: SpecIF:LifecycleStatusReleased
- SpecIF:multiple: false
- SpecIF:TextFormat: plain
- SpecIF:StringMaxLength: 32

## ReqIF-WF.SupplierComment (SpecIF:TermPropertyClassString)
- dcterms:identifier: PC-SupplierComment
- SpecIF:Revision: 1.2
- SpecIF:Origin: https://www.prostep.org/fileadmin/downloads/Recommendation_ReqIF_V2_RZ3.pdf
- SpecIF:Domain: Automotive Stakeholder Request Clarification Process
- SpecIF:LifecycleStatus: SpecIF:LifecycleStatusReleased
- SpecIF:multiple: true
- SpecIF:TextFormat: xhtml

## HIS:OemStatus (SpecIF:TermPropertyClassString)
- SpecIF:Origin: Hersteller-Initiative Software
- SpecIF:Domain: Automotive Stakeholder Request Clarification Process
- SpecIF:LifecycleStatus: SpecIF:LifecycleStatusEquivalent
- SpecIF:multiple: true

## HIS:OemComment (SpecIF:TermPropertyClassString)
- SpecIF:Origin: Hersteller-Initiative Software
- SpecIF:Domain: Automotive Stakeholder Request Clarification Process
- SpecIF:LifecycleStatus: SpecIF:LifecycleStatusEquivalent

## HIS:SupplierComment (SpecIF:TermPropertyClassString)
- SpecIF:Origin: Hersteller-Initiative Software
- SpecIF:Domain: Automotive Stakeholder Request Clarification Process
- SpecIF:LifecycleStatus: SpecIF:LifecycleStatusEquivalent
- SpecIF:multiple: true

## HIS:SupplierStatus (SpecIF:TermPropertyClassString)
- SpecIF:Origin: Hersteller-Initiative Software
- SpecIF:Domain: Automotive Stakeholder Request Clarification Process
- SpecIF:LifecycleStatus: SpecIF:LifecycleStatusEquivalent
- SpecIF:multiple: false

## Property Value Terms (SpecIF:Heading)
- dcterms:description: These are terms for certain enumerated property values. Not only the property titles, but also any enumerated value must be mapped between different systems or domains; therefore using defined terms is beneficial. Of course, like any other vocabulary term, a term used as property value for transmission or storage can be translated for display.

## SpecIF:priorityHigh (SpecIF:TermPropertyValue)
- dcterms:description: A value for property [[SpecIF:Priority]].
- SpecIF:LocalTerm: high
- SpecIF:Origin: http://specif.de
- SpecIF:Domain: Requirement Engineering, Automotive Stakeholder Request Clarification Process, System Model Integration
- SpecIF:LifecycleStatus: SpecIF:LifecycleStatusReleased

## SpecIF:priorityRatherHigh (SpecIF:TermPropertyValue)
- dcterms:description: A value for property [[SpecIF:Priority]].
- SpecIF:LocalTerm: rather high
- SpecIF:Origin: http://specif.de
- SpecIF:Domain: Requirement Engineering, Automotive Stakeholder Request Clarification Process, System Model Integration
- SpecIF:LifecycleStatus: SpecIF:LifecycleStatusReleased

## SpecIF:priorityMedium (SpecIF:TermPropertyValue)
- dcterms:description: A value for property [[SpecIF:Priority]].
- SpecIF:LocalTerm: medium
- SpecIF:Origin: http://specif.de
- SpecIF:Domain: Requirement Engineering, Automotive Stakeholder Request Clarification Process, System Model Integration
- SpecIF:LifecycleStatus: SpecIF:LifecycleStatusReleased

## SpecIF:priorityRatherLow (SpecIF:TermPropertyValue)
- dcterms:description: A value for property [[SpecIF:Priority]].
- SpecIF:LocalTerm: rather low
- SpecIF:Origin: http://specif.de
- SpecIF:Domain: Requirement Engineering, Automotive Stakeholder Request Clarification Process, System Model Integration
- SpecIF:LifecycleStatus: SpecIF:LifecycleStatusReleased

## SpecIF:priorityLow (SpecIF:TermPropertyValue)
- dcterms:description: A value for property [[SpecIF:Priority]].
- SpecIF:LocalTerm: low
- SpecIF:Origin: http://specif.de
- SpecIF:Domain: Requirement Engineering, Automotive Stakeholder Request Clarification Process, System Model Integration
- SpecIF:LifecycleStatus: SpecIF:LifecycleStatusReleased

## SpecIF:sizeXL (SpecIF:TermPropertyValue)
- dcterms:description: T-shirt sizes have become popular to classify [[IREB:Risk]], [[SpecIF:Damage]] or similar. Translates to 'very large' in English.
- SpecIF:Origin: http://specif.de
- SpecIF:LifecycleStatus: SpecIF:LifecycleStatusExperimental

## SpecIF:sizeL (SpecIF:TermPropertyValue)
- dcterms:description: T-shirt sizes have become popular to classify [[IREB:Risk]], [[SpecIF:Damage]] or similar. Translates to 'large' in English.
- SpecIF:Origin: http://specif.de
- SpecIF:LifecycleStatus: SpecIF:LifecycleStatusExperimental

## SpecIF:sizeM (SpecIF:TermPropertyValue)
- dcterms:description: T-shirt sizes have become popular to classify [[IREB:Risk]], [[SpecIF:Damage]] or similar. Translates to 'medium' in English.
- SpecIF:Origin: http://specif.de
- SpecIF:LifecycleStatus: SpecIF:LifecycleStatusExperimental

## SpecIF:sizeS (SpecIF:TermPropertyValue)
- dcterms:description: T-shirt sizes have become popular to classify [[IREB:Risk]], [[SpecIF:Damage]] or similar. Translates to 'small' in English.
- SpecIF:Origin: http://specif.de
- SpecIF:LifecycleStatus: SpecIF:LifecycleStatusExperimental

## SpecIF:sizeXS (SpecIF:TermPropertyValue)
- dcterms:description: T-shirt sizes have become popular to classify [[IREB:Risk]], [[SpecIF:Damage]] or similar. Translates to 'very small' in English.
- SpecIF:Origin: http://specif.de
- SpecIF:LifecycleStatus: SpecIF:LifecycleStatusExperimental

## SpecIF:LifecycleStatusRejected (SpecIF:TermPropertyValue)
- dcterms:description: A lifecycle status of a development artefact.
- SpecIF:LifecycleStatus: SpecIF:LifecycleStatusSubmitted

## SpecIF:LifecycleStatusPostponed (SpecIF:TermPropertyValue)
- dcterms:description: A lifecycle status of a development artefact.
- SpecIF:LifecycleStatus: SpecIF:LifecycleStatusSubmitted

## SpecIF:LifecycleStatusInitial (SpecIF:TermPropertyValue)
- dcterms:description: A lifecycle status of a development artefact.
- SpecIF:LifecycleStatus: SpecIF:LifecycleStatusSubmitted

## SpecIF:LifecycleStatusDrafted (SpecIF:TermPropertyValue)
- dcterms:description: A lifecycle status of a development artefact.
- SpecIF:LifecycleStatus: SpecIF:LifecycleStatusSubmitted

## SpecIF:LifecycleStatusSubmitted (SpecIF:TermPropertyValue)
- dcterms:description: A lifecycle status of a development artefact.

## SpecIF:LifecycleStatusApproved (SpecIF:TermPropertyValue)
- dcterms:description: A lifecycle status of a development artefact.
- SpecIF:LifecycleStatus: SpecIF:LifecycleStatusSubmitted

## SpecIF:LifecycleStatusReady (SpecIF:TermPropertyValue)
- dcterms:description: A lifecycle status of a development artefact. Meets the requirements of the "Definition of Ready" of the agile development method.
- SpecIF:LifecycleStatus: SpecIF:LifecycleStatusSubmitted

## SpecIF:LifecycleStatusDone (SpecIF:TermPropertyValue)
- dcterms:description: A lifecycle status of a development artefact. Meets the requirements of the "Definition of Done" of the agile development method.
- SpecIF:LifecycleStatus: SpecIF:LifecycleStatusSubmitted

## SpecIF:LifecycleStatusValidated (SpecIF:TermPropertyValue)
- dcterms:description: A lifecycle status of a development artefact.
- SpecIF:LifecycleStatus: SpecIF:LifecycleStatusSubmitted

## SpecIF:LifecycleStatusReleased (SpecIF:TermPropertyValue)
- dcterms:description: A lifecycle status of a development artefact.
- SpecIF:LifecycleStatus: SpecIF:LifecycleStatusSubmitted

## SpecIF:LifecycleStatusDeprecated (SpecIF:TermPropertyValue)
- dcterms:description: A lifecycle status of a development artefact.
- SpecIF:LifecycleStatus: SpecIF:LifecycleStatusSubmitted

## SpecIF:LifecycleStatusWithdrawn (SpecIF:TermPropertyValue)
- dcterms:description: A lifecycle status of a development artefact.
- SpecIF:LifecycleStatus: SpecIF:LifecycleStatusSubmitted

## SpecIF:EngineeringDisciplineMechanics (SpecIF:TermPropertyValue)
- SpecIF:Revision: 1.2
- dcterms:description: An engineering discipline addressed by a development artefact.
- SpecIF:Origin: https://specif.de
- SpecIF:Domain: Requirement Engineering, Automotive Stakeholder Request Clarification Process, System Model Integration
- SpecIF:LifecycleStatus: SpecIF:LifecycleStatusReleased

## SpecIF:EngineeringDisciplineElectronics (SpecIF:TermPropertyValue)
- SpecIF:Revision: 1.2
- dcterms:description: An engineering discipline addressed by a development artefact.
- SpecIF:Origin: https://specif.de
- SpecIF:Domain: Requirement Engineering, Automotive Stakeholder Request Clarification Process, System Model Integration
- SpecIF:LifecycleStatus: SpecIF:LifecycleStatusReleased

## SpecIF:EngineeringDisciplineSoftware (SpecIF:TermPropertyValue)
- SpecIF:Revision: 1.2
- dcterms:description: An engineering discipline addressed by a development artefact.
- SpecIF:Origin: https://specif.de
- SpecIF:Domain: Requirement Engineering, Automotive Stakeholder Request Clarification Process, System Model Integration
- SpecIF:LifecycleStatus: SpecIF:LifecycleStatusReleased

## SpecIF:EngineeringDisciplineSafety (SpecIF:TermPropertyValue)
- SpecIF:Revision: 1.2
- dcterms:description: An engineering discipline addressed by a development artefact.
- SpecIF:Origin: https://specif.de
- SpecIF:Domain: Requirement Engineering, Automotive Stakeholder Request Clarification Process, System Model Integration
- SpecIF:LifecycleStatus: SpecIF:LifecycleStatusReleased

## SpecIF:EngineeringDisciplineSecurity (SpecIF:TermPropertyValue)
- SpecIF:Revision: 1.2
- dcterms:description: An engineering discipline addressed by a development artefact.
- SpecIF:Origin: https://specif.de
- SpecIF:Domain: Requirement Engineering, Automotive Stakeholder Request Clarification Process, System Model Integration
- SpecIF:LifecycleStatus: SpecIF:LifecycleStatusReleased

## SpecIF:StakeholderGroupRegulation (SpecIF:TermPropertyValue)
- SpecIF:Revision: 1.2
- dcterms:description: A 'Stakeholder Group' addressed by a requirement.
- SpecIF:Origin: https://specif.de
- SpecIF:Domain: Requirement Engineering, Automotive Stakeholder Request Clarification Process, System Model Integration
- SpecIF:LifecycleStatus: SpecIF:LifecycleStatusReleased

## SpecIF:StakeholderGroupBusiness (SpecIF:TermPropertyValue)
- SpecIF:Revision: 1.2
- dcterms:description: A 'Stakeholder Group' addressed by a requirement.
- SpecIF:Origin: https://specif.de
- SpecIF:Domain: Requirement Engineering, Automotive Stakeholder Request Clarification Process, System Model Integration
- SpecIF:LifecycleStatus: SpecIF:LifecycleStatusReleased

## SpecIF:StakeholderGroupUser (SpecIF:TermPropertyValue)
- SpecIF:Revision: 1.2
- dcterms:description: A 'Stakeholder Group' addressed by a requirement.
- SpecIF:Origin: https://specif.de
- SpecIF:Domain: Requirement Engineering, Automotive Stakeholder Request Clarification Process, System Model Integration
- SpecIF:LifecycleStatus: SpecIF:LifecycleStatusReleased

## SpecIF:StakeholderGroupOperation (SpecIF:TermPropertyValue)
- SpecIF:Revision: 1.2
- dcterms:description: A 'Stakeholder Group' addressed by a requirement.
- SpecIF:Origin: https://specif.de
- SpecIF:Domain: Requirement Engineering, Automotive Stakeholder Request Clarification Process, System Model Integration
- SpecIF:LifecycleStatus: SpecIF:LifecycleStatusReleased

## SpecIF:Feature (SpecIF:TermPropertyValue)
- SpecIF:Revision: 1.2
- dcterms:description: A 'Feature' is an intentional distinguishing characteristic of a system, often a unique selling proposition.
- SpecIF:Origin: https://specif.de
- SpecIF:Domain: Requirement Engineering, Automotive Stakeholder Request Clarification Process, System Model Integration, Variant Management
- SpecIF:LifecycleStatus: SpecIF:LifecycleStatusReleased

## SpecIF:UserStory (SpecIF:TermPropertyValue)
- SpecIF:Revision: 1.2
- SpecIF:LocalTerm: User Story
- dcterms:description: A user story is an informal, general explanation of a software feature written from the perspective of the end user. Its purpose is to articulate how a software feature will provide value to the customer.
- SpecIF:Origin: https://www.atlassian.com/agile/project-management/user-stories
- SpecIF:Domain: Requirement Engineering, Automotive Stakeholder Request Clarification Process, System Model Integration, Variant Management
- SpecIF:LifecycleStatus: SpecIF:LifecycleStatusReleased

## IREB:FunctionalRequirement (SpecIF:TermPropertyValue)
- dcterms:description: A [[IREB:Requirement]] concerning a result of behavior that shall be provided by a functionof a system(or of a component or service).
- SpecIF:Origin: https://www.ireb.org/en/downloads/#cpre-glossary
- SpecIF:LifecycleStatus: SpecIF:LifecycleStatusReleased

## IREB:QualityRequirement (SpecIF:TermPropertyValue)
- dcterms:description: A [[IREB:Requirement]] that pertains to a quality concern that is not covered by functional requirements.
- SpecIF:Origin: https://www.ireb.org/en/downloads/#cpre-glossary
- SpecIF:LifecycleStatus: SpecIF:LifecycleStatusReleased

## IREB:Constraint (SpecIF:TermPropertyValue)
- dcterms:description: A [[IREB:Requirement]] that limits the solution space beyond what is necessary for meeting the given functional requirements and quality requirements.
- SpecIF:Origin: https://www.ireb.org/en/downloads/#cpre-glossary
- SpecIF:LifecycleStatus: SpecIF:LifecycleStatusReleased

## IREB:RequirementTypeFunction (SpecIF:TermPropertyValue)
- dcterms:description: A requirement concerning a result of behavior that shall be provided by a functionof a system(or of a component or service).
- SpecIF:Origin: https://www.ireb.org/en/downloads/#cpre-glossary
- SpecIF:LifecycleStatus: SpecIF:LifecycleStatusEquivalent

## IREB:RequirementTypeQuality (SpecIF:TermPropertyValue)
- dcterms:description: A [[IREB:Requirement]] that pertains to a quality concern that is not covered by functional requirements.
- SpecIF:Origin: https://www.ireb.org/en/downloads/#cpre-glossary
- SpecIF:LifecycleStatus: SpecIF:LifecycleStatusEquivalent

## IREB:RequirementTypeConstraint (SpecIF:TermPropertyValue)
- dcterms:description: A [[IREB:Requirement]] that limits the solution space beyond what is necessary for meeting the given functional requirements and quality requirements.
- SpecIF:Origin: https://www.ireb.org/en/downloads/#cpre-glossary
- SpecIF:LifecycleStatus: SpecIF:LifecycleStatusEquivalent

## IREB:Stakeholder (SpecIF:TermPropertyValue)
- dcterms:description: A person or organization that has a (direct or indirect) influence on a system’s requirements. Indirect influence also includes situations where a person or organization is impacted by the system.
  This is a subclass of [[FMC:Actor]], more precisely a value of it's property [[dcterms:type]].
- SpecIF:Origin: https://www.ireb.org/en/downloads/#cpre-glossary
- SpecIF:LifecycleStatus: SpecIF:LifecycleStatusReleased

## ReqIF-WF.CustomerStatus.NotToEvaluate (SpecIF:TermPropertyValue)
- dcterms:description: The requirement is relevant, but no evaluation is expected.
  - Attribute can be set to this value during the first transmission
  - Attribute can be changed to this value during the assessment process to indicate that a requirement must no longer be evaluated
  - Supplier can react with [[ReqIF-WF.SupplierStatus.ToBeClarified]] if he has objections to the non-evaluation. Otherwise, the SupplierStatus remains empty and the workflow ends.
- SpecIF:Origin: https://www.prostep.org/fileadmin/downloads/Recommendation_ReqIF_V2_RZ3.pdf
- SpecIF:Domain: Automotive Stakeholder Request Clarification Process
- SpecIF:LifecycleStatus: SpecIF:LifecycleStatusReleased

## ReqIF-WF.CustomerStatus.ToEvaluate (SpecIF:TermPropertyValue)
- dcterms:description: For the corresponding object an evaluation is expected by the supplier.
  - Attribute can be set to this value during the first transmission
  - Attribute can be changed to this value during the assessment process to indicate that a requirement has been modified and must be re-evaluated
- SpecIF:Origin: https://www.prostep.org/fileadmin/downloads/Recommendation_ReqIF_V2_RZ3.pdf
- SpecIF:Domain: Automotive Stakeholder Request Clarification Process
- SpecIF:LifecycleStatus: SpecIF:LifecycleStatusReleased

## ReqIF-WF.CustomerStatus.Accepted (SpecIF:TermPropertyValue)
- dcterms:description: The supplier evaluation is accepted by the customer.
- SpecIF:Origin: https://www.prostep.org/fileadmin/downloads/Recommendation_ReqIF_V2_RZ3.pdf
- SpecIF:Domain: Automotive Stakeholder Request Clarification Process
- SpecIF:LifecycleStatus: SpecIF:LifecycleStatusReleased

## ReqIF-WF.CustomerStatus.NotAccepted (SpecIF:TermPropertyValue)
- dcterms:description: The supplier evaluation is not accepted by the customer.
  - Setting this status terminates the evaluation for this object. The conflict must be solved in the further project course outside of this workflow.
- SpecIF:Origin: https://www.prostep.org/fileadmin/downloads/Recommendation_ReqIF_V2_RZ3.pdf
- SpecIF:Domain: Automotive Stakeholder Request Clarification Process
- SpecIF:LifecycleStatus: SpecIF:LifecycleStatusReleased

## ReqIF-WF.CustomerStatus.ToBeClarified (SpecIF:TermPropertyValue)
- dcterms:description: The requirement has to be clarified with the supplier. Details in [[ReqIF-WF.CustomerComment]].
- SpecIF:Origin: https://www.prostep.org/fileadmin/downloads/Recommendation_ReqIF_V2_RZ3.pdf
- SpecIF:Domain: Automotive Stakeholder Request Clarification Process
- SpecIF:LifecycleStatus: SpecIF:LifecycleStatusReleased

## ReqIF-WF.CustomerStatus.ProposedToDiscard (SpecIF:TermPropertyValue)
- dcterms:description: The requirement is marked as invalid and has to be discarded.

  NOTE: This value is OPTIONAL until the new ReqIF-WF process is well-established in industry.
- SpecIF:Origin: https://www.prostep.org/fileadmin/downloads/Recommendation_ReqIF_V2_RZ3.pdf
- SpecIF:Domain: Automotive Stakeholder Request Clarification Process
- SpecIF:LifecycleStatus: SpecIF:LifecycleStatusReleased

## ReqIF-WF.CustomerStatus.Discarded (SpecIF:TermPropertyValue)
- dcterms:description: The requirement has been marked explicitly as discarded by the customer.
- SpecIF:Origin: https://www.prostep.org/fileadmin/downloads/Recommendation_ReqIF_V2_RZ3.pdf
- SpecIF:Domain: Automotive Stakeholder Request Clarification Process
- SpecIF:LifecycleStatus: SpecIF:LifecycleStatusReleased

## ReqIF-WF.SupplierStatus.Agreed (SpecIF:TermPropertyValue)
- dcterms:description: The supplier accepts the requirement.
- SpecIF:Origin: https://www.prostep.org/fileadmin/downloads/Recommendation_ReqIF_V2_RZ3.pdf
- SpecIF:Domain: Automotive Stakeholder Request Clarification Process
- SpecIF:LifecycleStatus: SpecIF:LifecycleStatusReleased

## ReqIF-WF.SupplierStatus.NotAgreed (SpecIF:TermPropertyValue)
- dcterms:description: The supplier does not accept the requirement. Details must be declared in [[ReqIF-WF.SupplierComment]].
- SpecIF:Origin: https://www.prostep.org/fileadmin/downloads/Recommendation_ReqIF_V2_RZ3.pdf
- SpecIF:Domain: Automotive Stakeholder Request Clarification Process
- SpecIF:LifecycleStatus: SpecIF:LifecycleStatusReleased

## ReqIF-WF.SupplierStatus.AgreedWithComment (SpecIF:TermPropertyValue)
- dcterms:description: The supplier accepts the requirement with restrictions. The restrictions are explained by the supplier in the comment attribute [[ReqIF-WF.SupplierComment]].
- SpecIF:Origin: https://www.prostep.org/fileadmin/downloads/Recommendation_ReqIF_V2_RZ3.pdf
- SpecIF:Domain: Automotive Stakeholder Request Clarification Process
- SpecIF:LifecycleStatus: SpecIF:LifecycleStatusReleased

## ReqIF-WF.SupplierStatus.ToBeClarified (SpecIF:TermPropertyValue)
- dcterms:description: The supplier requires clarification. The supplier must actively clarify the matter with the customer. Details must be declared in [[ReqIF-WF.SupplierComment]].
- SpecIF:Origin: https://www.prostep.org/fileadmin/downloads/Recommendation_ReqIF_V2_RZ3.pdf
- SpecIF:Domain: Automotive Stakeholder Request Clarification Process
- SpecIF:LifecycleStatus: SpecIF:LifecycleStatusReleased

## ReqIF-WF.SupplierStatus.DiscardedDeployed (SpecIF:TermPropertyValue)
- dcterms:description: The supplier confirms that he will not implement the discarded requirement.
- SpecIF:Origin: https://www.prostep.org/fileadmin/downloads/Recommendation_ReqIF_V2_RZ3.pdf
- SpecIF:Domain: Automotive Stakeholder Request Clarification Process
- SpecIF:LifecycleStatus: SpecIF:LifecycleStatusReleased

## SpecIF:UserRole (SpecIF:TermPropertyValue)
- dcterms:description: This is a subclass of [[FMC:Actor]]; more precisely a value of it's property [[dcterms:type]].
- SpecIF:LifecycleStatus: SpecIF:LifecycleStatusExperimental

## bpmn:startEvent (SpecIF:TermPropertyValue)
- dcterms:description: A defined value for the [[dcterms:type]] property of [[FMC:Event]] when used to represent a general start event.
- SpecIF:Origin: https://camunda.com/bpmn/reference/
- SpecIF:LifecycleStatus: SpecIF:LifecycleStatusExperimental

## bpmn:intermediateEvent (SpecIF:TermPropertyValue)
- dcterms:description: A defined value for the [[dcterms:type]] property of [[FMC:Event]] when used to represent a general intermediate event.
- SpecIF:Origin: https://camunda.com/bpmn/reference/
- SpecIF:LifecycleStatus: SpecIF:LifecycleStatusExperimental

## bpmn:endEvent (SpecIF:TermPropertyValue)
- dcterms:description: A defined value for the [[dcterms:type]] property of [[FMC:Event]] when used to represent a general end event.
- SpecIF:Origin: https://camunda.com/bpmn/reference/
- SpecIF:LifecycleStatus: SpecIF:LifecycleStatusExperimental

## bpmn:processStep (SpecIF:TermPropertyValue)
- dcterms:description: A defined value for the [[dcterms:type]] property of [[FMC:Actor]] when used to represent a process step.
- SpecIF:LifecycleStatus: SpecIF:LifecycleStatusExperimental

## bpmn:join (SpecIF:TermPropertyValue)
- dcterms:description: A defined value for the [[dcterms:type]] property of [[FMC:Actor]] when used to represent a 'Join' element in models created with BPMN.
- SpecIF:LifecycleStatus: SpecIF:LifecycleStatusExperimental

## bpmn:timer (SpecIF:TermPropertyValue)
- dcterms:description: A defined value for the [[dcterms:type]] property of [[FMC:Actor]] when used to represent a 'Timer' element in models created with BPMN.
- SpecIF:LifecycleStatus: SpecIF:LifecycleStatusExperimental

## Statements
- SpecIF:satisfies SpecIF:isSynonymOf oslc_rm:satisfies
- SpecIF:Stereotype SpecIF:isSynonymOf dcterms:type
- SpecIF:SubClass SpecIF:isSynonymOf dcterms:type
- oslc_rm:satisfiedBy SpecIF:isAntonymOf oslc_rm:satisfies
- oslc_rm:elaboratedBy SpecIF:isAntonymOf oslc_rm:elaborates
- oslc_rm:specifiedBy SpecIF:isAntonymOf oslc_rm:specifies
- oslc_rm:decomposedBy SpecIF:isAntonymOf oslc_rm:decomposes
- oslc_rm:constrainedBy SpecIF:isAntonymOf oslc_rm:constrains
- follows SpecIF:isAntonymOf SpecIFF:precedes
- SysML:isGeneralizationOf SpecIF:isAntonymOf SysML:isSpecializationOf
- SpecIF:sameAs SpecIF:isSynonymOf owl:sameAs
- SpecIF:Outline SpecIF:isSynonymOf SpecIF:Hierarchy
- SpecIF:Id SpecIF:isSynonymOf dcterms:identifier
- SpecIF:createdBy SpecIF:isSynonymOf dcterms:creator
- SpecIF:createdAt SpecIF:isSynonymOf dcterms:created
- SpecIF:changedAt SpecIF:isSynonymOf dcterms:modified
- SpecIF:Creation SpecIF:isSynonymOf SpecIF:Instantiation
- SpecIF:Source SpecIF:isSynonymOf SpecIF:Subject
- SpecIF:Target SpecIF:isSynonymOf SpecIF:Object
- IREB:RequirementTypeFunction SpecIF:isSynonymOf IREB:FunctionalRequirement
- IREB:RequirementTypeQuality SpecIF:isSynonymOf IREB:QualityRequirement
- IREB:RequirementTypeConstraint SpecIF:isSynonymOf IREB:Constraint
- SpecIF:isInverseOf SpecIF:isSynonymOf SpecIF:isAntonymOf
- SpecIF:Stereotype SpecIF:isSynonymOf UML:Stereotype
- UML:Stereotype SpecIF:isSynonymOf dcterms:type
- SpecIF:SubClass SpecIF:isSynonymOf UML:Stereotype
- FMC:Actor SpecIF:isEligibleAsSubject SpecIF:reads
- FMC:State SpecIF:isEligibleAsObject SpecIF:reads
- FMC:Actor SpecIF:isEligibleAsSubject SpecIF:writes
- FMC:State SpecIF:isEligibleAsObject SpecIF:writes
- FMC:Actor SpecIF:isEligibleAsSubject SpecIF:stores
- FMC:State SpecIF:isEligibleAsObject SpecIF:stores
- SpecIF:signals SpecIF:isSpecializationOf SpecIFF:precedes
- SpecIF:triggers SpecIF:isSpecializationOf SpecIFF:precedes
- SpecIF:receivesFrom SpecIF:isAntonymOf SpecIF:sendsTo
- SpecIF:sendsTo SpecIF:isSpecializationOf SpecIF:communicatesWith
- SpecIF:receivesFrom SpecIF:isSpecializationOf SpecIF:communicatesWith
- FMC:Actor SpecIF:isEligibleAsSubject SpecIF:serves
- FMC:Actor SpecIF:isEligibleAsObject SpecIF:serves
- SysML:isSpecialisationOf SpecIF:isSynonymOf SysML:isSpecializationOf
- SysML:isGeneralisationOf SpecIF:isSynonymOf SysML:isGeneralizationOf
- HIS:OemStatus SpecIF:isSynonymOf ReqIF-WF.CustomerStatus
- HIS:SupplierComment SpecIF:isSynonymOf ReqIF-WF.SupplierComment
- HIS:SupplierStatus SpecIF:isSynonymOf ReqIF-WF.SupplierStatus
- HIS:OemComment SpecIF:isSynonymOf ReqIF-WF.CustomerComment
- SysML:isGeneralisationOf SpecIF:isAntonymOf SysML:isSpecialisationOf
- W3C:Vocabulary SpecIF:isSynonymOf W3C:Ontology
- SpecIF:Priority SpecIF:hasEnumValue SpecIF:priorityHigh
- SpecIF:Priority SpecIF:hasEnumValue SpecIF:priorityRatherHigh
- SpecIF:Priority SpecIF:hasEnumValue SpecIF:priorityMedium
- SpecIF:Priority SpecIF:hasEnumValue SpecIF:priorityRatherLow
- SpecIF:Priority SpecIF:hasEnumValue SpecIF:priorityLow
- SpecIF:LifecycleStatus SpecIF:hasEnumValue SpecIF:LifecycleStatusInitial
- SpecIF:LifecycleStatus SpecIF:hasEnumValue SpecIF:LifecycleStatusDrafted
- SpecIF:LifecycleStatus SpecIF:hasEnumValue SpecIF:LifecycleStatusSubmitted
- SpecIF:LifecycleStatus SpecIF:hasEnumValue SpecIF:LifecycleStatusApproved
- SpecIF:LifecycleStatus SpecIF:hasEnumValue SpecIF:LifecycleStatusReady
- SpecIF:LifecycleStatus SpecIF:hasEnumValue SpecIF:LifecycleStatusDone
- SpecIF:LifecycleStatus SpecIF:hasEnumValue SpecIF:LifecycleStatusValidated
- SpecIF:LifecycleStatus SpecIF:hasEnumValue SpecIF:LifecycleStatusReleased
- SpecIF:LifecycleStatus SpecIF:hasEnumValue SpecIF:LifecycleStatusDeprecated
- SpecIF:LifecycleStatus SpecIF:hasEnumValue SpecIF:LifecycleStatusWithdrawn
- SpecIF:LifecycleStatus SpecIF:hasEnumValue SpecIF:LifecycleStatusPostponed
- SpecIF:LifecycleStatus SpecIF:hasEnumValue SpecIF:LifecycleStatusRejected
- IREB:Requirement SpecIF:isEligibleAsSubject IREB:refines
- IREB:Requirement SpecIF:isEligibleAsObject IREB:refines
- SpecIF:Paragraph SpecIF:hasProperty dcterms:title
- SpecIF:Paragraph SpecIF:hasProperty dcterms:description
- SpecIF:commentRefersTo SpecIF:isSpecializationOf SpecIF:refersTo
- SpecIF:Comment SpecIF:isEligibleAsSubject SpecIF:commentRefersTo
- FMC:Actor SpecIF:isEligibleAsObject SpecIF:commentRefersTo
- FMC:State SpecIF:isEligibleAsObject SpecIF:commentRefersTo
- FMC:Event SpecIF:isEligibleAsObject SpecIF:commentRefersTo
- SpecIF:Hierarchy SpecIF:hasProperty dcterms:title
- SpecIF:Hierarchy SpecIF:hasProperty dcterms:description
- SpecIF:Hierarchy SpecIF:hasProperty dcterms:type
- SpecIF:Paragraph SpecIF:hasProperty SpecIF:Diagram
- SpecIF:Paragraph SpecIF:hasProperty dcterms:type
- SpecIF:View SpecIF:isSpecializationOf SpecIF:Paragraph
- FMC:Plan SpecIF:isSynonymOf SpecIF:View
- SpecIF:Diagram SpecIF:isSynonymOf SpecIF:View
- SpecIF:View SpecIF:hasProperty SpecIF:Notation
- SpecIF:Heading SpecIF:isSpecializationOf SpecIF:Paragraph
- SpecIF:Paragraph SpecIF:isEligibleAsObject SpecIF:commentRefersTo
- SpecIF:Heading SpecIF:isEligibleAsObject SpecIF:commentRefersTo
- SpecIF:View SpecIF:isEligibleAsObject SpecIF:commentRefersTo
- SpecIF:ModelElement SpecIF:hasProperty dcterms:title
- SpecIF:ModelElement SpecIF:hasProperty dcterms:description
- SpecIF:ModelElement SpecIF:hasProperty dcterms:type
- FMC:Actor SpecIF:isSpecializationOf SpecIF:ModelElement
- FMC:State SpecIF:isSpecializationOf SpecIF:ModelElement
- FMC:Event SpecIF:isSpecializationOf SpecIF:ModelElement
- SpecIF:Collection SpecIF:isSpecializationOf SpecIF:ModelElement
- SpecIF:View SpecIF:isEligibleAsSubject SpecIF:shows
- FMC:Actor SpecIF:isEligibleAsObject SpecIF:shows
- FMC:State SpecIF:isEligibleAsObject SpecIF:shows
- FMC:Event SpecIF:isEligibleAsObject SpecIF:shows
- SpecIF:Collection SpecIF:isEligibleAsObject SpecIF:shows
- SpecIF:Collection SpecIF:isEligibleAsObject SpecIF:commentRefersTo
- SpecIF:Comment SpecIF:hasProperty dcterms:description
- IREB:Requirement SpecIF:isSpecializationOf SpecIF:Paragraph
- IREB:Requirement SpecIF:hasProperty SpecIF:Priority
- SpecIF:Feature SpecIF:isSpecializationOf SpecIF:Paragraph
- SpecIF:Feature SpecIF:hasProperty SpecIF:Priority
- ReqIF-WF:Requirement SpecIF:isSpecializationOf IREB:Requirement
- ReqIF-WF:Requirement SpecIF:hasProperty ReqIF-WF.SupplierStatus
- ReqIF-WF:Requirement SpecIF:hasProperty ReqIF-WF.SupplierComment
- ReqIF-WF:Requirement SpecIF:hasProperty ReqIF-WF.CustomerStatus
- ReqIF-WF:Requirement SpecIF:hasProperty ReqIF-WF.CustomerComment
- ReqIF-WF.SupplierStatus SpecIF:hasEnumValue ReqIF-WF.SupplierStatus.ToBeClarified
- ReqIF-WF.SupplierStatus SpecIF:hasEnumValue ReqIF-WF.SupplierStatus.AgreedWithComment
- ReqIF-WF.SupplierStatus SpecIF:hasEnumValue ReqIF-WF.SupplierStatus.Agreed
- ReqIF-WF.SupplierStatus SpecIF:hasEnumValue ReqIF-WF.SupplierStatus.NotAgreed
- ReqIF-WF.SupplierStatus SpecIF:hasEnumValue ReqIF-WF.SupplierStatus.DiscardedDeployed
- ReqIF-WF.CustomerStatus SpecIF:hasEnumValue ReqIF-WF.CustomerStatus.ToEvaluate
- ReqIF-WF.CustomerStatus SpecIF:hasEnumValue ReqIF-WF.CustomerStatus.ToBeClarified
- ReqIF-WF.CustomerStatus SpecIF:hasEnumValue ReqIF-WF.CustomerStatus.NotAccepted
- ReqIF-WF.CustomerStatus SpecIF:hasEnumValue ReqIF-WF.CustomerStatus.Accepted
- ReqIF-WF.CustomerStatus SpecIF:hasEnumValue ReqIF-WF.CustomerStatus.NotToEvaluate
- ReqIF-WF.CustomerStatus SpecIF:hasEnumValue ReqIF-WF.CustomerStatus.ProposedToDiscard
- ReqIF-WF.CustomerStatus SpecIF:hasEnumValue ReqIF-WF.CustomerStatus.Discarded
- SpecIF:EngineeringDiscipline SpecIF:hasEnumValue SpecIF:EngineeringDisciplineMechanics
- SpecIF:EngineeringDiscipline SpecIF:hasEnumValue SpecIF:EngineeringDisciplineElectronics
- SpecIF:EngineeringDiscipline SpecIF:hasEnumValue SpecIF:EngineeringDisciplineSoftware
- SpecIF:EngineeringDiscipline SpecIF:hasEnumValue SpecIF:EngineeringDisciplineSafety
- SpecIF:EngineeringDiscipline SpecIF:hasEnumValue SpecIF:EngineeringDisciplineSecurity
- IREB:Requirement SpecIF:isEligibleAsSubject oslc_rm:satisfies
- ReqIF-WF:Requirement SpecIF:isEligibleAsSubject oslc_rm:satisfies
- FMC:Actor SpecIF:isEligibleAsObject oslc_rm:satisfies
- FMC:Event SpecIF:isEligibleAsObject oslc_rm:satisfies
- FMC:State SpecIF:isEligibleAsObject oslc_rm:satisfies
- SpecIF:Collection SpecIF:isEligibleAsObject oslc_rm:satisfies
- IREB:Requirement SpecIF:isEligibleAsObject oslc_rm:satisfiedBy
- ReqIF-WF:Requirement SpecIF:isEligibleAsObject oslc_rm:satisfiedBy
- FMC:Actor SpecIF:isEligibleAsSubject oslc_rm:satisfiedBy
- FMC:State SpecIF:isEligibleAsSubject oslc_rm:satisfiedBy
- FMC:Event SpecIF:isEligibleAsSubject oslc_rm:satisfiedBy
- SpecIF:Collection SpecIF:isEligibleAsSubject oslc_rm:satisfiedBy
- SpecIF:TermResourceClass SpecIF:isSpecializationOf SpecIF:OntologyTerm
- SpecIF:TermStatementClass SpecIF:isSpecializationOf SpecIF:OntologyTerm
- SpecIF:TermPropertyClass SpecIF:isSpecializationOf SpecIF:OntologyTerm
- SpecIF:TermPropertyValue SpecIF:isSpecializationOf SpecIF:OntologyTerm
- bpmn:group SpecIF:isSynonymOf SpecIF:Collection
- oslc_rm:elaborates SpecIF:isSynonymOf IREB:refines
- IREB:Requirement SpecIF:hasProperty IREB:RequirementType
- ReqIF-WF:Requirement SpecIF:isEligibleAsSubject IREB:refines
- ReqIF-WF:Requirement SpecIF:isEligibleAsObject IREB:refines
- IREB:Requirement SpecIF:isEligibleAsSubject SpecIF:duplicates
- ReqIF-WF:Requirement SpecIF:isEligibleAsSubject SpecIF:duplicates
- IREB:Requirement SpecIF:isEligibleAsObject SpecIF:duplicates
- ReqIF-WF:Requirement SpecIF:isEligibleAsObject SpecIF:duplicates
- IREB:Requirement SpecIF:isEligibleAsSubject SpecIF:contradicts
- ReqIF-WF:Requirement SpecIF:isEligibleAsSubject SpecIF:contradicts
- IREB:Requirement SpecIF:isEligibleAsObject SpecIF:contradicts
- ReqIF-WF:Requirement SpecIF:isEligibleAsObject SpecIF:contradicts
- SpecIF:Perspective SpecIF:isSynonymOf SpecIF:StakeholderGroup
- IREB:Requirement SpecIF:hasProperty SpecIF:StakeholderGroup
- SpecIF:StakeholderGroup SpecIF:hasEnumValue SpecIF:StakeholderGroupRegulation
- SpecIF:StakeholderGroup SpecIF:hasEnumValue SpecIF:StakeholderGroupBusiness
- SpecIF:StakeholderGroup SpecIF:hasEnumValue SpecIF:StakeholderGroupUser
- SpecIF:StakeholderGroup SpecIF:hasEnumValue SpecIF:StakeholderGroupOperation
- SpecIF:Feature SpecIF:isSynonymOf IREB:Requirement
- IREB:RequirementType SpecIF:hasEnumValue SpecIF:Feature
- IREB:RequirementType SpecIF:hasEnumValue SpecIF:UserStory
- IREB:RequirementType SpecIF:hasEnumValue IREB:FunctionalRequirement
- IREB:RequirementType SpecIF:hasEnumValue IREB:QualityRequirement
- IREB:RequirementType SpecIF:hasEnumValue IREB:Constraint
- SpecIF:stores SpecIF:isSynonymOf SpecIF:accesses
- SpecIF:reads SpecIF:isSpecializationOf SpecIF:accesses
- SpecIF:writes SpecIF:isSpecializationOf SpecIF:accesses
- FMC:modifies SpecIF:isSynonymOf SpecIF:accesses
- FMC:Actor SpecIF:isEligibleAsSubject follows
- FMC:Actor SpecIF:isEligibleAsObject follows
- FMC:Actor SpecIF:isEligibleAsSubject SpecIFF:precedes
- FMC:Actor SpecIF:isEligibleAsObject SpecIFF:precedes
- FMC:Actor SpecIF:isEligibleAsSubject SpecIF:communicatesWith
- FMC:Actor SpecIF:isEligibleAsObject SpecIF:communicatesWith
- FMC:Actor SpecIF:isEligibleAsSubject SpecIF:sendsTo
- FMC:Actor SpecIF:isEligibleAsObject SpecIF:sendsTo
- FMC:Actor SpecIF:isEligibleAsSubject SpecIF:receivesFrom
- FMC:Actor SpecIF:isEligibleAsObject SpecIF:receivesFrom
- FMC:Actor SpecIF:isEligibleAsSubject SpecIF:accesses
- FMC:State SpecIF:isEligibleAsObject SpecIF:accesses
- IREB:Requirement SpecIF:isEligibleAsSubject SpecIF:dependsOn
- ReqIF-WF:Requirement SpecIF:isEligibleAsSubject SpecIF:dependsOn
- IREB:Requirement SpecIF:isEligibleAsObject SpecIF:dependsOn
- ReqIF-WF:Requirement SpecIF:isEligibleAsObject SpecIF:dependsOn
- IREB:Requirement SpecIF:isEligibleAsSubject SysML:traces
- ReqIF-WF:Requirement SpecIF:isEligibleAsSubject SysML:traces
- IREB:Requirement SpecIF:isEligibleAsObject SysML:traces
- ReqIF-WF:Requirement SpecIF:isEligibleAsObject SysML:traces
- IREB:Requirement SpecIF:isEligibleAsSubject SysML:isDerivedFrom
- ReqIF-WF:Requirement SpecIF:isEligibleAsSubject SysML:isDerivedFrom
- IREB:Requirement SpecIF:isEligibleAsObject SysML:isDerivedFrom
- ReqIF-WF:Requirement SpecIF:isEligibleAsObject SysML:isDerivedFrom
- FMC:Actor SpecIF:isEligibleAsSubject SysML:isComposedOf
- FMC:Actor SpecIF:isEligibleAsObject SysML:isComposedOf
- FMC:Actor SpecIF:isEligibleAsSubject SysML:isAggregatedBy
- FMC:Actor SpecIF:isEligibleAsObject SysML:isAggregatedBy
- FMC:Actor SpecIF:isEligibleAsSubject SysML:extends
- FMC:Actor SpecIF:isEligibleAsObject SysML:extends
- FMC:Actor SpecIF:isEligibleAsSubject SysML:includes
- FMC:Actor SpecIF:isEligibleAsObject SysML:includes
- FMC:Actor SpecIF:isEligibleAsSubject SysML:isAllocatedTo
- FMC:Actor SpecIF:isEligibleAsObject SysML:isAllocatedTo
- FMC:State SpecIF:isEligibleAsSubject SysML:isAssociatedWith
- FMC:State SpecIF:isEligibleAsObject SysML:isAssociatedWith
- FMC:Actor SpecIF:isEligibleAsSubject SpecIF:contains
- FMC:State SpecIF:isEligibleAsSubject SpecIF:contains
- FMC:Actor SpecIF:isEligibleAsObject SpecIF:contains
- FMC:State SpecIF:isEligibleAsObject SpecIF:contains
- FMC:Event SpecIF:isEligibleAsObject SpecIF:contains
- ArchiMate:unites SpecIF:isSpecializationOf SpecIF:contains
- FMC:contains SpecIF:isSpecializationOf SpecIF:contains
- SpecIF:Collection SpecIF:isEligibleAsSubject SpecIF:contains
- FMC:Actor SpecIF:isEligibleAsSubject FMC:contains
- FMC:State SpecIF:isEligibleAsSubject FMC:contains
- FMC:Actor SpecIF:isEligibleAsObject FMC:contains
- FMC:State SpecIF:isEligibleAsObject FMC:contains
- FMC:Event SpecIF:isEligibleAsObject FMC:contains
- SpecIF:Collection SpecIF:isEligibleAsObject SpecIF:contains
- FMC:Actor SpecIF:isEligibleAsSubject SysML:composes
- FMC:Actor SpecIF:isEligibleAsObject SysML:composes
- SysML:isComposedOf SpecIF:isAntonymOf SysML:composes
- SysML:isAggregatedBy SpecIF:isAntonymOf SysML:aggregates
- FMC:Actor SpecIF:isEligibleAsSubject SysML:aggregates
- FMC:Actor SpecIF:isEligibleAsObject SysML:aggregates
- oslc_rm:decomposes SpecIF:isSynonymOf SysML:isComposedOf
- oslc_rm:decomposedBy SpecIF:isSynonymOf SysML:composes
- SpecIF:contains SpecIF:hasProperty dcterms:type
- FMC:Plan SpecIF:isSpecializationOf SpecIF:Paragraph
- FMC:Plan SpecIF:isEligibleAsObject SpecIF:commentRefersTo
- FMC:Plan SpecIF:isEligibleAsSubject SpecIF:shows
- ReqIF.Text SpecIF:isSynonymOf dcterms:description
- ReqIF.Name SpecIF:isSynonymOf dcterms:title
- ReqIF.ForeignID SpecIF:isSynonymOf dcterms:identifier
- ReqIF.ForeignState SpecIF:isSynonymOf SpecIF:LifecycleStatus
- ReqIF.Category SpecIF:isSynonymOf dcterms:type
- ArchiMate:Viewpoint SpecIF:isSpecializationOf SpecIF:Paragraph
- ArchiMate:Viewpoint SpecIF:hasProperty SpecIF:Notation
- ArchiMate:Viewpoint SpecIF:isEligibleAsObject SpecIF:commentRefersTo
- ArchiMate:Viewpoint SpecIF:isEligibleAsSubject SpecIF:shows
- ArchiMate:Viewpoint SpecIF:isSynonymOf SpecIF:View
- FMC:Plan SpecIF:hasProperty SpecIF:Notation
- SpecIF:Outline SpecIF:hasProperty SpecIF:LifecycleStatus
- SpecIF:Hierarchy SpecIF:hasProperty SpecIF:LifecycleStatus
- SpecIF:Outline SpecIF:isSpecializationOf SpecIF:Paragraph
- SpecIF:BillOfMaterials SpecIF:isSpecializationOf SpecIF:Outline
- SpecIF:BusinessProcesses SpecIF:isPluralOf SpecIF:BusinessProcess
- SpecIF:BusinessProcess SpecIF:isSpecializationOf SpecIF:View
- SpecIF: SpecIF:isNamespace SpecIF:Paragraph
- SpecIF: SpecIF:isNamespace SpecIF:Heading
- SpecIF: SpecIF:isNamespace SpecIF:View
- Archimate: SpecIF:isNamespace ArchiMate:Viewpoint
- SpecIF: SpecIF:isNamespace SpecIF:Diagram
- SpecIF: SpecIF:isNamespace SpecIF:Feature
- IREB: SpecIF:isNamespace IREB:Requirement
