# Project 'Related Terms'
- Rights: Creative Commons 4.0 CC BY-SA, https://creativecommons.org/licenses/by-sa/4.0/

## Vehicle (Resource Term)

## Lorry (Resource Term)

## Statements
- Vehicle uml:Generalization Lorry
