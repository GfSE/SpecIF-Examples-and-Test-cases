# Requirement with Multilanguage-Content D
- Rights: Creative Commons 4.0 CC BY-SA, https://creativecommons.org/licenses/by-sa/4.0/

## Minimum button size (IREB:Requirement)
- dcterms:description: The button size MUST not be less than 20mm in diameter.
- SpecIF:Priority: Rather High
