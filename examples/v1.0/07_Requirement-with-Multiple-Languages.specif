# Project 'Requirement with Multiple Languages'

## Minimum button size (IREB:Requirement)
- dcterms:description: The button size MUST not be less than 20mm in diameter.
- SpecIF:Priority: Rather High
