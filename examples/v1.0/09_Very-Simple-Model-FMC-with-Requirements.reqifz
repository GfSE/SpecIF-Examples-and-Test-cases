# Project 'Very Simple Model (FMC) with Requirements'

# Specification: Project 'Very Simple Model (FMC) with Requirements'
- ReqIF.Name: Project 'Very Simple Model (FMC) with Requirements'

## R1: Requirements (SpecIF:Heading)

### R2: Data Volume (IREB:Requirement)
The data store MUST support a total volume up to 850 GB.
- SpecIF:Priority: SpecIF:priorityRatherHigh

### R3: Consistency (IREB:Requirement)
The data store MUST be consistent at all times.
- SpecIF:Priority: SpecIF:priorityHigh

### R4: Response Time (IREB:Requirement)
The system SHOULD respond on user queries within 300 ms.
- SpecIF:Priority: SpecIF:priorityMedium

## R5: System Model (SpecIF:Heading)

### R6: IT-Integration: FiCo-Application and FiCo-Data (SpecIF:Diagram)
- SpecIF:Diagram: Model Diagram:
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- SpecIF:shows -> R7
- SpecIF:shows -> R8

#### R7: FiCo-Application (FMC:Actor)
IT-Application for Finance and Controlling.
- SpecIF:writes -> R8
- SpecIF:reads -> R8
- oslc_rm:satisfies -> R4

#### R8: FiCo-Data (FMC:State)
Finance and Controlling Data, such as cost-units per project with budget, accrued cost etc.
- oslc_rm:satisfies -> R2
- oslc_rm:satisfies -> R3

## R9: SpecIF:Glossary (SpecIF:Heading)

### R10: FMC:Actors (SpecIF:Heading)

### R11: FMC:States (SpecIF:Heading)

### R12: FMC:Events (SpecIF:Heading)

### R13: SpecIF:Collections (SpecIF:Heading)
