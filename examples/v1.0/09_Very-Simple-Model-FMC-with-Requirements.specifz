# Project 'Very Simple Model (FMC) with Requirements'
- Rights: Creative Commons 4.0 CC BY-SA, https://creativecommons.org/licenses/by-sa/4.0/

## Requirements (SpecIF:Heading)

## System Model (SpecIF:Heading)

## IT-Integration: FiCo-Application and FiCo-Data (SpecIF:Diagram)
- SpecIF:Diagram: Model Diagram:
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- dcterms:type: FMC Block Diagram

## FiCo-Application (FMC:Actor)
- dcterms:description: IT-Application for Finance and Controlling.

## FiCo-Data (FMC:State)
- dcterms:description: Finance and Controlling Data, such as cost-units per project with budget, accrued cost etc.

## Consistency (IREB:Requirement)
- dcterms:description: The data store MUST be consistent at all times.
- SpecIF:Priority: SpecIF:priorityHigh

## Data Volume (IREB:Requirement)
- dcterms:description: The data store MUST support a total volume up to 850 GB.
- SpecIF:Priority: SpecIF:priorityRatherHigh

## Response Time (IREB:Requirement)
- dcterms:description: The system SHOULD respond on user queries within 300 ms.
- SpecIF:Priority: SpecIF:priorityMedium

## Statements
- IT-Integration: FiCo-Application and FiCo-Data SpecIF:shows FiCo-Application
- IT-Integration: FiCo-Application and FiCo-Data SpecIF:shows FiCo-Data
- FiCo-Application SpecIF:writes FiCo-Data
- FiCo-Application SpecIF:reads FiCo-Data
- FiCo-Data oslc_rm:satisfies Data Volume
- FiCo-Data oslc_rm:satisfies Consistency
- FiCo-Application oslc_rm:satisfies Response Time
