# Project 'Very Simple Model (FMC)'
- Rights: Creative Commons 4.0 CC BY-SA, https://creativecommons.org/licenses/by-sa/4.0/

## IT-Integration: FiCo-Application and FiCo-Data (SpecIF:Diagram)
- SpecIF:Diagram: Model Diagram:
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- dcterms:type: FMC Block Diagram

## FiCo-Application (FMC:Actor)
- dcterms:description: IT-Application for Finance and Controlling.

## FiCo-Data (FMC:State)
- dcterms:description: Finance and Controlling Data, such as cost-units per project with budget, accrued cost etc.

## Statements
- IT-Integration: FiCo-Application and FiCo-Data SpecIF:shows FiCo-Application
- IT-Integration: FiCo-Application and FiCo-Data SpecIF:shows FiCo-Data
- FiCo-Application SpecIF:writes FiCo-Data
- FiCo-Application SpecIF:reads FiCo-Data
