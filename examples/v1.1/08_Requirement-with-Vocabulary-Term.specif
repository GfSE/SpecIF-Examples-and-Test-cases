# Project 'Requirement with Vocabulary Term'

## Minimum button size (IREB:Requirement)
- dcterms:description: The button size MUST not be less than 20mm in diameter.
- SpecIF:Priority: SpecIF:priorityLow
