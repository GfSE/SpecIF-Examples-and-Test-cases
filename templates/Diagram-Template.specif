# A template for diagrams
- Rights: Creative Commons 4.0 CC BY-SA, https://creativecommons.org/licenses/by-sa/4.0/

## Add diagram title here (IREB:Requirement)
- dcterms:description: Add description here
- SpecIF:Diagram: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Diagram Title
- dcterms:type: Sonstiger Typ
