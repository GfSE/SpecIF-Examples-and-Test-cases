# Case-Study SmAV with SysML
System Specification of a Small Autonomous Vehicle built with Lego Mindstorm EV3 Kit.
- Rights: Creative Commons 4.0 CC BY-SA, https://creativecommons.org/licenses/by-sa/4.0/

## Requirements (SpecIF:Heading)

## Functions (SpecIF:Heading)

## Logical Solution (SpecIF:Heading)

## Physical Solution (SpecIF:Heading)
