# Projektvorgehen-Beispiel (2020-02-23)
Diese Applikations-Landkarte gehört zu einem Prozess gleichen Namens. In diesem Beispiel wird die Modellintegration mittels SpecIF demonstriert. Hierzu wird zuerst der SpecIF-Export aus ARCWAY geladen und dann der Prozess mit der Methode 'Adopt' hinzugefügt. Bereits existierende Modellelemente gleichen Namens (dcterms:title) und Typs werden vom Prozess übernommen und so entsteht das semantisch integrierte Modell.
- Rights: Creative Commons 4.0 CC BY-SA, https://creativecommons.org/licenses/by-sa/4.0/

## Projektinformation (SpecIF:Heading)
- dcterms:description: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
  Diese Applikations-Landkarte gehört zu einem Prozess gleichen Namens. In diesem Beispiel wird die Modellintegration mittels SpecIF demonstriert. Hierzu wird zuerst der SpecIF-Export aus ARCWAY geladen und dann der Prozess mit der Methode 'Adopt' hinzugefügt. Bereits existierende Modellelemente gleichen Namens (dcterms:title) und Typs werden vom Prozess übernommen und so entsteht das semantisch integrierte Modell.
  Projektbeteiligte:
  | Name | Organisation | Telefon | Email |
  | --- | --- | --- | --- |
  | Dr. Oskar von Dungern | adesso AG | +49 162 2808 376 | oskar.dungern@adesso.de |
  Legende:
  Zur Unterscheidung ihres Typs ist den Elementnamen eines der folgenden Symbole vorangestellt:
  | ▣ | Plan | Ein 'Plan' ist eine graphische Modellsicht zur Vermittlung eines bestimmten Sachverhalts, z.B. ein Geschäftsprozess oder Systemaufbau. |
  | --- | --- | --- |
  | ■ | Akteur (Rolle, Funktion) | Ein 'Akteur' ist ein fundamentaler Modellelement-Typ für ein aktives Objekt, z.B. eine Aktivität, ein Prozess-Schritt, eine Funktion, eine Systemkomponente oder eine Rolle. |
  | ● | Zustand (Information) | Ein 'Zustand' ist ein fundamentaler Modellelement-Typ für ein passives Objekt, z.B. ein Wert, ein Dokument, ein Informationsspeicher oder eine physische Beschaffenheit. |
  | ♦ | Ereignis | Ein 'Ereignis' ist ein fundamentaler Modellelement-Typ für eine zeitliche Referenz, eine Änderung einer Bedingung bzw. eines Zustandes oder generell ein Synchronisations-Mittel. |
  | ✶ | Produktmerkmal | Ein 'Produktmerkmal' ist eine beabsichtigte differenzierende Eigenschaft eines Systems, oft ein Alleinstellungsmerkmal. |
  | ↯ | Anforderung | Eine 'Anforderung' ist ein einzelnes dokumentiertes physisches oder funktionales Bedürfnis, das der betreffende Entwurf, das Produkt oder der Prozess erfüllen muss. |
  | ☛ | Annotation | Eine Interaction-Room 'Annotation' weist auf einen Punkt besonderen Interesses hin. Hierzu gehören Werte, die Kundenbedürfnisse widerspiegeln oder positiven Effekt auf die Ziele der Organisation haben, Produkteigenschaften, deren Umsetzung Nutzen/Aufwand verursacht, und Herausforderungen, die während der Entwicklung zu berücksichtigen sind. |

## Projektziele (SpecIF:Heading)

## Landkarten (SpecIF:Heading)
- dcterms:description: Aus den originalen Wandtafel-Skizzen des IR-Workshops entwickelte Landkarten in fachlicher Notation und nach Interesse detailliert.

## Annotationen (SpecIF:Heading)

## Anforderungen (SpecIF:Heading)

## Anhang: Methoden (SpecIF:Heading)

## Interaction Room (SpecIF:Heading)
- dcterms:description: Die Interaction Room (IR) Methode bringt Vertreter von Fachabteilung, IT und Management zusammen und nimmt abwechselnd verschiedene Perspektiven ein, nämlich:
  - Prozesse und Nutzungsfälle
  - Bebauung mit Applikationen/Systemen und ihren Schnittstellen
  - Fachobjekte
  - Annotationen heben besonders zu beachtende Gesichtspunkte/Anforderungen hervor.
  Die Perspektiven wachsen zusammen und werden jeweils dort detailliert, wo aktuell Handlungsbedarf oder der Wunsch nach besserer Einsicht besteht. Interessierende fachliche Nutzungsfälle werden heran gezogen und analysiert; so werden Stück um Stück alle Fachobjekte identifiziert, die benötigten Funktionen definiert und den geeigneten Systemen zugeordnet. Die Nutzungsfälle werden schließlich als "User-Stories" ausgearbeitet und für die agile Implementierung priorisiert.
  Vorgehen und Nutzen des Interaction Room zusammen gefasst:
  - Mit informellen Skizzen beginnen, Formalismen bewusst zurückstellen,
  - Mit Annotationen die besonders wichtigen Aspekte hervor heben,
  - Durch Perspektivwechsel Lücken und Inkonsistenzen entdecken
  - Die Zusammenhänge erkennen und dokumentieren.

## Vernetzte Prozess- und IT-Dokumentation (SpecIF:Heading)
- dcterms:description: Das Vorgehen basiert auf dem "Fundamental Modelling Concept" (FMC), welches von Prof. Siegfried Wendt an der Universität Kaiserslautern und am Hasso-Plattner-Institut in Potsdam konzipiert wurde. Es bringt dynamische und statische Sichten ("Ablauf und Aufbau") sowie die Anforderungen in Zusammenhang und vermittelt ein gemeinsames Verständnis zwischen allen Beteiligten.
  Ebenso wie ein Generalbebauungsplan die Basis für die Stadtplanung ist, helfen geeignete Diagramme bei der Beschreibung von Software-Systemen. Die Vernetzung der verschiedenen Sichten Ablauf, Aufbau und Anforderungen hat einen konkreten Nutzen:
  - Die sich ergänzenden Sichten unterstützen besonders effektiv eine Prüfung auf Widerspruchsfreiheit, Vollständigkeit und Realisierbarkeit.
  - Die Anforderungen werden den Funktionen und Systemkomponenten zugeordnet, so dass gezielt recherchiert werden kann, wo welche Anforderungen zu berücksichtigen sind. Damit einher geht eine einfachere Auswirkungsanalyse im Falle einer Anforderungsänderung ('Traceability').
  - Die Aufwandsschätzung ist genauer und Kostentreiber sind identifizierbar und lokalisierbar.
  - Die Kommunikation zwischen Auftraggeber und Auftragnehmer wird klarer.
  - Das Projektrisiko wird beträchtlich eingeschränkt.
  Auch wenn im Interaction Room Workshop die Modelle zunächst informell erfasst werden("Soft Modeling"), werden daraus im Zuge der weiteren Konzeption entsprechende Diagramme mit einem Modellierungswerkzeug erzeugt. Alle dargestellten Modellelemente werden identifiziert und in einer zentralen Ablage ("Repository") verwaltet. Alle so erfassten Modellelemente sind im Kapitel "Glossar" alphabetisch aufgeführt. Jedes Modellelement kennt seine Vorkommen auf verschiedenen Modelldiagrammen ... und wenn Titel, Beschreibung oder ein anders Attribut verändert werden, werden automatisch alle Diagramme aktualisiert.
  Weiterhin werden Projektziele, Annotationen und andere Anforderungen tabellarisch erfasst und einzeln den betroffenen Modellelementen zugeordnet. Dadurch weiß jede Anforderung, welche Modellelemente betroffen sind und jedes Modellelement kennt alle sie betreffenden Anforderungen.
  In einer generierten WORD-Datei werden diese Beziehungen als klickbare Hyperlinks aufgenommen; bei der Publikation des Inhalts im Web können darüber hinaus weitere automatisch ermittelte Beziehungen verfolgt werden. In der Praxis und speziell bei größeren Projekten zeigt sich, dass die Einsicht in die Zusammenhänge signifikant verbessert wird; Lücken und Inkonsistenzen werden früher sichtbar.
  Siehe auch:
  - http://www.f-m-c.org
  - Andreas Knöpfel, Bernhard Gröne, Peter Tabeling: Fundamental Modelling Concepts - Effective Communication of IT-Systems, Wiley & Sons, 2006
  - http://specif.de/files/resources/enso-m/documents-de/TdSE-2015_Dungern_Modellintegration-mit-fuenf-fundamentalen-Elementtypen_(Text).pdf
  - http://specif.de/files/resources/adesso/docs-de/ReCONF-2017_Dungern-Uphoff_Interaction-Room-SpecIF.pdf

## Modellelemente (Glossar) (SpecIF:Heading)
- dcterms:type: SpecIF:Glossary

## Typ 'Akteur' (SpecIF:Heading)
- dcterms:description: Ein 'Akteur' ist ein fundamentaler Modellelement-Typ für ein aktives Objekt, z.B. eine Aktivität, ein Prozess-Schritt, eine Funktion, eine Systemkomponente oder eine Rolle.

## Typ 'Zustand' (SpecIF:Heading)
- dcterms:description: Ein 'Zustand' ist ein fundamentaler Modellelement-Typ für ein passives Objekt, z.B. ein Wert, ein Dokument, ein Informationsspeicher oder eine physische Beschaffenheit.

## Typ 'Ereignis' (SpecIF:Heading)
- dcterms:description: Ein 'Ereignis' ist ein fundamentaler Modellelement-Typ für eine zeitliche Referenz, eine Änderung einer Bedingung bzw. eines Zustandes oder generell ein Synchronisations-Mittel.

## Bebauungsplan (SpecIF:Diagram)
- dcterms:description: Die Landkarte der beteiligten IT-Applikationen mit ihren Schnittstellen und den ausgetauschten Fachobjekten.
- SpecIF:Diagram: Plan:
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- SpecIF:Notation: FMC Block Diagram
- PC-Diagram-custom.IR-canvas-type: System-Integration

## Fachobjekte (SpecIF:Diagram)
- dcterms:description: Hier werden die Fachobjekte und ihre Beziehungen in Form eines UML-Klassendiagramms dargestellt.
- SpecIF:Diagram: Plan:
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- SpecIF:Notation: UML Class Diagram

## Arbeitsumgebung (SpecIF:Diagram)
- dcterms:description: Der IR lebt von der informellen und bewegten Interaktion in einer kreativen Atmosphäre.
- SpecIF:Diagram: Plan:
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- SpecIF:Notation: FMC Block Diagram

## Interaction Room im Entwicklungsprozess (SpecIF:Diagram)
- dcterms:description: Der Interaction Room ist mit Vorteil im Vorfeld der Entwicklung einzusetzen. Nach einer Kreativ-Phase, beispielsweise unter Einsatz von "Design-Thinking", kommen Anwender und Umsetzer in Interaction-Room Workshops zusammen, um Prozesse, Systemstrukturen und Anforderungen zu erfassen und in Einklang zu bringen. Auf dieser Basis werden bestimmte herausfordernde Szenarien einem User-Experience Design unter enger Einbindung der Anwender unterzogen. Ziel ist es Dialog-Layouts und Abläufe zu optimieren und eine hohe Benutzerfreundlichkeit zu erzielen. Auf Basis der Ergebnisse aus Interaction-Room und User-Experience-Design werden die zu realisierenden User-Stories detailiert und für die agile Entwicklung priorisiert.
  Der ganze Entwicklungs-Prozess wird regelmäßig und iterativ durchgeführt, um neue Anforderungen aufzugreifen, im Konzept zu verankern und auf Machbarkeit zu prüfen, ehe sie in die Entwicklung kommen.
  Die Dokumentation des Interaction-Rooms stellt die übergreifenden Zusammenhänge dar, in denen die User-Stories der Entwicklungs-Backlogs verortet werden können. Hierzu ist die vernetzte Prozess- und IT-Dokumentation, die im nächsten Kapitel behandelt wird, besonders gut geeignet.
- SpecIF:Diagram: Plan:
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- SpecIF:Notation: ACM Process Diagram

## Perspektiven (SpecIF:Diagram)
- dcterms:description: In unterschiedlichen Perspektiven werden
  - die Geschäftsprozesse
  - die (Teil-) Systeme und ihre Schnittstellen, und
  - die Fachobjekte
  betrachtet. Indem alle zugleich auf verschiedenen Wänden sichtbar sind, lassen sich Zusammenhänge und Abhängigkeiten leichter erkennen.
- SpecIF:Diagram: Plan:
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- SpecIF:Notation: FMC Block Diagram

## Logische Vernetzung der Modellelemente (SpecIF:Diagram)
- dcterms:description: Diagramme und Modellelemente aller Notationen lassen sich anhand ihres fundamentalen Typs einteilen:
  - Ein 'Plan' (oder 'Diagramm') ist eine graphische Modellsicht zur Vermittlung eines bestimmten Sachverhalts, z.B. ein Geschäftsprozess oder Systemaufbau.
  - Ein 'Akteur' ist ein fundamentaler Modellelement-Typ für ein aktives Objekt, z.B. eine Aktivität, ein Prozess-Schritt, eine Funktion, eine Systemkomponente oder eine Rolle.
  - Ein 'Zustand' ist ein fundamentaler Modellelement-Typ für ein passives Objekt, z.B. ein Wert, ein Dokument, ein Informationsspeicher oder eine physische Beschaffenheit.
  - Ein 'Ereignis' ist ein fundamentaler Modellelement-Typ für eine zeitliche Referenz, eine Änderung einer Bedingung bzw. eines Zustandes oder generell ein Synchronisations-Mittel.
  - Eine 'Anforderung' ist ein einzelnes dokumentiertes physisches oder funktionales Bedürfnis, das der betreffende Entwurf, das Produkt oder der Prozess erfüllen muss.
  - Ein 'Merkmal' ist eine beabsichtigte differenzierende Eigenschaft eines Systems, oft ein Alleinstellungsmerkmal.
  Zwischen Diagrammen und Modellelementen werden explizit semantische Beziehungen hergestellt; in den meisten Fällen automatisch durch graphische Analyse der Modelldiagramme, beispielsweise:
  - Ein Plan 'zeigt' einen Akteur, einen Zustand oder ein Ereignis. Dadurch weiß jedes Element auf welchen Plänen es vorkommt.
  - Eine Benutzerrolle (Akteur) nutzt ('enthält') einen Dialog (Akteur).
  - Eine Komponente (Akteur) realisiert ('enthält') einen Dialog (Akteur).
  - und viele andere mehr.
  Weitere Beziehungen siond manuell zu erzeugen, z.B.:
  - Eine Komponente 'erfüllt' eine Anforderungen. Schließlich kennt jede Komponente ihre Anforderungen und bei Änderung einer Anforderung sind sofort die betroffenen Komponenten zu ersehen.
- SpecIF:Diagram: Plan:
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- SpecIF:Notation: FMC Block Diagram

## Notation: Fachdatenmodell (SpecIF:Diagram)
- dcterms:description: .. gemäß Unified Modeling Language (UML)
- SpecIF:Diagram: Plan:
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- SpecIF:Notation: UML Class Diagram

## Notation: Geschäftsprozess (SpecIF:Diagram)
- dcterms:description: Business Process Models gemäß Business Process Model and Notation (BPMN).
- SpecIF:Diagram: Plan:
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- SpecIF:Notation: BPMN Process Model

## Notation: IT Landkarte (SpecIF:Diagram)
- dcterms:description: System composition gemäß Fundamental Modelling Concepts (FMC).
- SpecIF:Diagram: Plan:
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- SpecIF:Notation: FMC Block Diagram

## Werkzeug-Kette (SpecIF:Diagram)
- SpecIF:Diagram: Plan:
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- SpecIF:Notation: FMC Block Diagram

## Anforderung (FMC:State)

## Anfrage (FMC:State)
- dcterms:description: Anfrage des Kunden

## Angebot (FMC:State)
- dcterms:description: Angebot als Reaktion auf die Anfrage des Kunden.

## Angebots-Nr (FMC:State)

## Applikations-Landkarte (FMC:State)

## ARCWAY Cockpit (FMC:Actor)

## Auftrag (FMC:State)
- dcterms:description: Auftrag des Kunden - Hurra, wir haben gewonnen.

## Auftrags-Nr (FMC:State)

## BPMN Workflow-Engine (FMC:Actor)

## BPMN-XML (FMC:State)

## BPMN-XML Export (FMC:Actor)

## BPMN-XML Import (FMC:Actor)

## Camunda-Modeller (FMC:Actor)

## Controlling (FMC:Actor)

## Delivery (FMC:Actor)

## DMS (FMC:Actor)
- dcterms:description: Zentrales Dokumenten-Archiv

## ePub Export (FMC:Actor)

## FiCo (FMC:Actor)
- dcterms:description: Finanzen und Controlling

## FiCo-Daten (FMC:State)
- dcterms:description: Finanz- und Controllingdaten eines Projekts wie Kostenträger, Budget, Budgetausschöpfung, etc. In der anderen Richtung werden aufgelaufene Aufwände und Kosten gemeldet.

## Interner Projektauftrag (FMC:State)
- dcterms:description: Projektauftrag an das ausführende Team ("Delivery").

## MS Excel (FMC:Actor)

## Objekt-Landkarte (FMC:State)
- dcterms:description: .. dargestellt als UML Klassendiagramm

## Original-Diagramm (FMC:State)

## Projekt-Nr (FMC:State)

## Projektakte (FMC:State)

## Projektplan (FMC:State)
- dcterms:description: Der initiale und fortgeschriebene aktuelle Projektplan.

## Prozess-Modell (FMC:State)

## ReqIF Export (FMC:Actor)

## SpecIF (FMC:State)

## SpecIF Export (FMC:Actor)

## SpecIF Import (FMC:Actor)

## SpecIF Integrator and Viewer (FMC:Actor)

## Vernetzte Modellelemente (FMC:State)

## Vertrieb (FMC:Actor)

## WORD Export (FMC:Actor)

## Workflow: Projektvorgehen (FMC:Actor)

## XLSX (FMC:State)

## XLSX Import (FMC:Actor)

## Auftragsdaten ins FiCo-System (IR:Annotation)
- dcterms:identifier: ANN_001
- dcterms:description: Aktuell werden die Auftragsdaten vom Einkauf manuell in das FiCo-System übernommen. Kann ein elektronischer Datenaustausch (wie GAEB beim Bau) mit den Kunden vereinbart werden?
- SpecIF:Priority: hoch (L)
- PC-Ann-custom.IR-annotation-class: Werte-Treiber
- PC-Ann-custom.IR-annotation-subclass: Wertvoll für den Anwender
- PC-Ann-custom.IR-annotation-benefit: mittel (M)
- PC-Ann-custom.IR-annotation-risk: klein (S)
- PC-Ann-custom.IR-annotation-frequency: klein (S)
- PC-Ann-custom.IR-annotation-difficulty: mittel (M)

## Statements
- Bebauungsplan SpecIF:shows Anfrage
- Bebauungsplan SpecIF:shows Angebot
- Bebauungsplan SpecIF:shows Auftrag
- Bebauungsplan SpecIF:shows Controlling
- Bebauungsplan SpecIF:shows Delivery
- Bebauungsplan SpecIF:shows DMS
- Bebauungsplan SpecIF:shows FiCo
- Bebauungsplan SpecIF:shows FiCo-Daten
- Bebauungsplan SpecIF:shows Interner Projektauftrag
- Bebauungsplan SpecIF:shows Projektplan
- Bebauungsplan SpecIF:shows Vertrieb
- Bebauungsplan SpecIF:shows Workflow: Projektvorgehen
- Fachobjekte SpecIF:shows Anfrage
- Fachobjekte SpecIF:shows Angebot
- Fachobjekte SpecIF:shows Angebots-Nr
- Fachobjekte SpecIF:shows Auftrag
- Fachobjekte SpecIF:shows Auftrags-Nr
- Fachobjekte SpecIF:shows Interner Projektauftrag
- Fachobjekte SpecIF:shows Projekt-Nr
- Fachobjekte SpecIF:shows Projektakte
- Fachobjekte SpecIF:shows Projektplan
- Werkzeug-Kette SpecIF:shows Anforderung
- Werkzeug-Kette SpecIF:shows Applikations-Landkarte
- Werkzeug-Kette SpecIF:shows ARCWAY Cockpit
- Werkzeug-Kette SpecIF:shows BPMN Workflow-Engine
- Werkzeug-Kette SpecIF:shows BPMN-XML
- Werkzeug-Kette SpecIF:shows BPMN-XML Export
- Werkzeug-Kette SpecIF:shows BPMN-XML Import
- Werkzeug-Kette SpecIF:shows Camunda-Modeller
- Werkzeug-Kette SpecIF:shows ePub Export
- Werkzeug-Kette SpecIF:shows MS Excel
- Werkzeug-Kette SpecIF:shows Objekt-Landkarte
- Werkzeug-Kette SpecIF:shows Original-Diagramm
- Werkzeug-Kette SpecIF:shows Prozess-Modell
- Werkzeug-Kette SpecIF:shows ReqIF Export
- Werkzeug-Kette SpecIF:shows SpecIF
- Werkzeug-Kette SpecIF:shows SpecIF Export
- Werkzeug-Kette SpecIF:shows SpecIF Import
- Werkzeug-Kette SpecIF:shows SpecIF Integrator and Viewer
- Werkzeug-Kette SpecIF:shows Vernetzte Modellelemente
- Werkzeug-Kette SpecIF:shows WORD Export
- Werkzeug-Kette SpecIF:shows XLSX
- Werkzeug-Kette SpecIF:shows XLSX Import
- Anfrage SpecIF:contains Projekt-Nr
- Angebot SpecIF:contains Angebots-Nr
- Angebot SpecIF:contains Projekt-Nr
- ARCWAY Cockpit SpecIF:contains Applikations-Landkarte
- ARCWAY Cockpit SpecIF:contains Objekt-Landkarte
- ARCWAY Cockpit SpecIF:contains SpecIF Export
- Auftrag SpecIF:contains Auftrags-Nr
- Auftrag SpecIF:contains Projekt-Nr
- BPMN Workflow-Engine SpecIF:reads BPMN-XML
- BPMN-XML Export SpecIF:writes BPMN-XML
- BPMN-XML Export SpecIF:reads Prozess-Modell
- BPMN-XML Import SpecIF:reads BPMN-XML
- Camunda-Modeller SpecIF:contains BPMN-XML Export
- Camunda-Modeller SpecIF:contains Prozess-Modell
- Workflow: Projektvorgehen SpecIF:sendsTo Controlling
- Workflow: Projektvorgehen SpecIF:sendsTo Delivery
- DMS SpecIF:writes Anfrage
- DMS SpecIF:reads Anfrage
- DMS SpecIF:writes Angebot
- DMS SpecIF:reads Angebot
- DMS SpecIF:writes Auftrag
- DMS SpecIF:reads Auftrag
- DMS SpecIF:writes Interner Projektauftrag
- DMS SpecIF:reads Interner Projektauftrag
- DMS SpecIF:writes Projektplan
- DMS SpecIF:reads Projektplan
- FiCo SpecIF:writes FiCo-Daten
- FiCo SpecIF:reads FiCo-Daten
- Interner Projektauftrag SpecIF:contains Projekt-Nr
- MS Excel SpecIF:contains Anforderung
- MS Excel SpecIF:writes XLSX
- Projektakte SpecIF:contains Anfrage
- Projektakte SpecIF:contains Angebot
- Projektakte SpecIF:contains Auftrag
- Projektakte SpecIF:contains Interner Projektauftrag
- Projektakte SpecIF:contains Projekt-Nr
- Projektakte SpecIF:contains Projektplan
- Projektplan SpecIF:contains Projekt-Nr
- SpecIF Export SpecIF:writes SpecIF
- SpecIF Export SpecIF:reads Applikations-Landkarte
- SpecIF Export SpecIF:reads Objekt-Landkarte
- SpecIF Import SpecIF:reads SpecIF
- SpecIF Integrator and Viewer SpecIF:contains BPMN-XML Import
- SpecIF Integrator and Viewer SpecIF:contains ePub Export
- SpecIF Integrator and Viewer SpecIF:contains Original-Diagramm
- SpecIF Integrator and Viewer SpecIF:contains ReqIF Export
- SpecIF Integrator and Viewer SpecIF:contains SpecIF Export
- SpecIF Integrator and Viewer SpecIF:contains SpecIF Import
- SpecIF Integrator and Viewer SpecIF:contains Vernetzte Modellelemente
- SpecIF Integrator and Viewer SpecIF:contains WORD Export
- SpecIF Integrator and Viewer SpecIF:contains XLSX Import
- Workflow: Projektvorgehen SpecIF:sendsTo Vertrieb
- Workflow: Projektvorgehen SpecIF:writes Anfrage
- Workflow: Projektvorgehen SpecIF:reads Anfrage
- Workflow: Projektvorgehen SpecIF:writes Angebot
- Workflow: Projektvorgehen SpecIF:reads Angebot
- Workflow: Projektvorgehen SpecIF:writes Auftrag
- Workflow: Projektvorgehen SpecIF:reads Auftrag
- Workflow: Projektvorgehen SpecIF:writes FiCo-Daten
- Workflow: Projektvorgehen SpecIF:reads FiCo-Daten
- Workflow: Projektvorgehen SpecIF:writes Interner Projektauftrag
- Workflow: Projektvorgehen SpecIF:reads Interner Projektauftrag
- Workflow: Projektvorgehen SpecIF:writes Projektplan
- Workflow: Projektvorgehen SpecIF:reads Projektplan
- Controlling SpecIF:sendsTo Workflow: Projektvorgehen
- Delivery SpecIF:sendsTo Workflow: Projektvorgehen
- Vertrieb SpecIF:sendsTo Workflow: Projektvorgehen
- XLSX Import SpecIF:reads XLSX
- Auftragsdaten ins FiCo-System IR:refersTo Auftrag
- Auftragsdaten ins FiCo-System IR:refersTo FiCo
