# A test with formatted characters
- Rights: Creative Commons 4.0 CC BY-SA, https://creativecommons.org/licenses/by-sa/4.0/

## a text with some character formatting, colors as RGB Hex like '#008000' (SpecIF:Paragraph)
- dcterms:title: Text with some character formatting, colors as RGB Hex like '#008000'
- dcterms:description: Lorem {ipsum (bold)} dolor [sit (italic)] amet, {consetetur sadipscing (emphasized)}[elitr (span #FF0000)], sed diam {nonumy (span #0000FF, bold)} [eirmod{tempor (span #008000)}(emphasized)], no {[sea (bold)]takimata (emphasized)} Mojito!.
