# A test with text containing an ordered list
- Rights: Creative Commons 4.0 CC BY-SA, https://creativecommons.org/licenses/by-sa/4.0/

## ordered-list (SpecIF:Paragraph)
- dcterms:title: Text with ordered-list
- dcterms:description: Text before list
  1. first {item (italic)}
  2. zweiter Punkt
  3. troisième élément
  Text after list
