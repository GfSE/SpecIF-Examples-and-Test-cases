# A test with special characters
- Rights: Creative Commons 4.0 CC BY-SA, https://creativecommons.org/licenses/by-sa/4.0/

## a text with some special characters (resource title) (SpecIF:Paragraph)
- dcterms:title: Text with some special characters like '<' and '&' (title property)
- dcterms:description: I am < 2m tall & my weight is >20kg.
