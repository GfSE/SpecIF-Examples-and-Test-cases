# Example text with a table
- Rights: Creative Commons 4.0 CC BY-SA, https://creativecommons.org/licenses/by-sa/4.0/

## a simple table (SpecIF:Paragraph)
- dcterms:title: Text with a simple table
- dcterms:description:
  | Name | Organisation | Telephone | Email |
  | --- | --- | --- | --- |
  | Dr. Oskar Surname | adesso AG |  | oskar.surname@adesso.de |

## a simple table with thead section (SpecIF:Paragraph)
- dcterms:title: Text with a simple table having a thead section
- dcterms:description:
  | Name | Organisation | Telephone | Email |
  | --- | --- | --- | --- |
  | Dr. Oskar Surname | adesso AG |  | oskar.surname@adesso.de |
