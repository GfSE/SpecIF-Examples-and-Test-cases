# A test with text containing Umlaut and other non-ASCII characters
- Rights: Creative Commons 4.0 CC BY-SA, https://creativecommons.org/licenses/by-sa/4.0/

## SpecIF:Paragraph (SpecIF:Paragraph)
- dcterms:title: Projektinformation
- dcterms:description: Ae Äber
  Oe Öber
  Ue Über
  ae äber
  oe öber
  ue über
  sz großer Baum
