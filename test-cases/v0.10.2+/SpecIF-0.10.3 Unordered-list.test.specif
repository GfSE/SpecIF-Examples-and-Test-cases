# A test with text containing an unordered list
- Rights: Creative Commons 4.0 CC BY-SA, https://creativecommons.org/licenses/by-sa/4.0/

## SpecIF:Paragraph (SpecIF:Paragraph)
- dcterms:title: Text with unordered-list
- dcterms:description: Text before list:
  - first item
  - zweiter [Punkt (bold)]
  - troisième élément
  Text after list.
