# A test with duplicate-id
- Rights: Creative Commons 4.0 CC BY-SA, https://creativecommons.org/licenses/by-sa/4.0/

## a text with some special characters (resource title) (SpecIF:Paragraph)
- dcterms:title: Text with some special characters (title property)
- dcterms:description: I am < 2m tall and my weight is >20kg.

## a text with some special characters (resource title) (SpecIF:Paragraph)
- dcterms:title: Text with some special characters (title property)
- dcterms:description: I am < 2m tall and my weight is >20kg.

## a text with some special characters (resource title) (SpecIF:Paragraph)
- dcterms:title: Text with some special characters (title property)
- dcterms:description: I am < 2m tall and my weight is >20kg.
