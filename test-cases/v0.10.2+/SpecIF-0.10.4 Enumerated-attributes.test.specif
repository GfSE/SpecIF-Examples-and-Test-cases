# Resource with enumerated properties (2018-04-30)
- Rights: Creative Commons 4.0 CC BY-SA, https://creativecommons.org/licenses/by-sa/4.0/

## Resource with enumerated properties (IREB:Requirement)
- dcterms:identifier: Sec_005
- dcterms:description: This resource has three enumerated properties; 'Status' and 'Priority' are single-valued, 'Discipline' is multi-valued.
  'Priority' is special, as it has no title attribute; so the title should be taken from the resource's class.
- SpecIF:Status: 30_submitted
- PT-Req-Priority: 1_high
- Discipline: Electronics, Software
