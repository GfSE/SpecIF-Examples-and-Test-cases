# External link (project title)
- Rights: Creative Commons 4.0 CC BY-SA, https://creativecommons.org/licenses/by-sa/4.0/

## Project Information 21 (SpecIF:Paragraph)
- dcterms:title: Link with an <a>..</a> tag pair
- dcterms:description: A link referencing an external resource like <a href="https://specif.de">SpecIF Initiative</a>: SpecIF Initiative. Some more text.

## Project Information 22 (SpecIF:Paragraph)
- dcterms:title: Simple link which must be linkified by the program to work
- dcterms:description: A simple link referencing an external resource: --> https://specif.de. Some more text.
