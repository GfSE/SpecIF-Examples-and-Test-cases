# A test with formatted text
- Rights: Creative Commons 4.0 CC BY-SA, https://creativecommons.org/licenses/by-sa/4.0/

## unordered-list (SpecIF:Paragraph)
- dcterms:title: Text with unordered-list
- dcterms:description: Text before list:
  - first item
  - zweiter [Punkt (bold)]
  - troisième élément
  Text after list.

## ordered-list (SpecIF:Paragraph)
- dcterms:title: Text with ordered-list
- dcterms:description: Text before list:
  1. first {item (italic)}
  2. zweiter Punkt
  3. troisième élément
  Text after list.

## multiple paragraphs (SpecIF:Paragraph)
- dcterms:title: Text with multiple paragraphs
- dcterms:description: First paragraph, an empty paragraph follows:
  Nächster Absatz.
  Lorem ipsum dolor sit amet, consetetur sadipscing elitr, sed diam nonumy eirmod tempor invidunt ut labore et dolore magna aliquyam erat, sed diam voluptua. At vero eos et accusam et justo duo dolores et ea rebum. Stet clita kasd gubergren, no sea takimata sanctus est Lorem ipsum dolor sit amet. Lorem ipsum dolor sit amet, consetetur sadipscing elitr, sed diam nonumy eirmod tempor invidunt ut labore et dolore magna aliquyam erat, sed diam voluptua. At vero eos et accusam et justo duo dolores et ea rebum. Stet clita kasd gubergren,
  no sea takimata sanctus est Lorem ipsum dolor sit amet.
  Dernier paragraphe.

## a simple table (SpecIF:Paragraph)
- dcterms:title: Text with a simple table
- dcterms:description:
  | Name | Organisation | Telephone | Email |
  | --- | --- | --- | --- |
  | Oskar Surname | adesso AG |  | oskar.surname@adesso.de |

## a simple table with thead section (SpecIF:Paragraph)
- dcterms:title: Text with a simple table having a thead section
- dcterms:description:
  | Name | Organisation | Telephone | Email |
  | --- | --- | --- | --- |
  | Oskar Surname | adesso AG |  | oskar.surname@adesso.de |

## a text with some character formatting, colors as HTML literal like 'green' (SpecIF:Paragraph)
- dcterms:title: Text with some character formatting, colors as HTML literal like 'green'
- dcterms:description: Lorem {ipsum (bold)} dolor [sit (italic)] amet, {consetetur sadipscing (emphasized)}[elitr (span red)], sed diam {nonumy (span blue, bold)} [eirmod{tempor (span green)}(emphasized)], no {[sea (bold)]takimata (emphasized)} Mojito!

## a text with some character formatting, colors as RGB Hex like '#008000' (SpecIF:Paragraph)
- dcterms:title: Text with some character formatting, colors as RGB Hex like '#008000'
- dcterms:description: Lorem {ipsum (bold)} dolor [sit (italic)] amet, {consetetur sadipscing (emphasized)}[elitr (span #FF0000)], sed diam {nonumy (span #0000FF, bold)} [eirmod{tempor (span #008000)}(emphasized)], no {[sea (bold)]takimata (emphasized)} Mojito!.

## a text with some special characters (resource title) (SpecIF:Paragraph)
- dcterms:title: Text with some special characters (title property)
- dcterms:description: I am < 2m tall and my weight is >20kg.

## A resource with enumerated properties (IREB:Requirement)
- dcterms:identifier: Sec_005
- dcterms:title: A resource with enumerated properties (title property)
- dcterms:description: This resource has two properties with enumerated values; the second has no title and so it's class's title should be displayed.
- SpecIF:Status: 30_submitted
- PT-Req-Priority: 1_high
