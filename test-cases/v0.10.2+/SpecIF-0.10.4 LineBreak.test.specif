# A test with text containing a line-break and a non-ASCII character
- Rights: Creative Commons 4.0 CC BY-SA, https://creativecommons.org/licenses/by-sa/4.0/

## SpecIF:Paragraph (SpecIF:Paragraph)
- dcterms:title: Projektinformation
- dcterms:description: Ein Text vor dem Zeilenumbruch
  und ein weiterer nach demselben, ähh.
