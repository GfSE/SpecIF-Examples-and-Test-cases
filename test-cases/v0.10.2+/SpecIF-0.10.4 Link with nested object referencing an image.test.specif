# Link with nested object referencing an image (project title)
- Rights: Creative Commons 4.0 CC BY-SA, https://creativecommons.org/licenses/by-sa/4.0/

## Project Information (SpecIF:Paragraph)
- dcterms:title: Link with an embedded full object tag pair
- dcterms:description: A link with a nested object referencing an image like <a href="https://adesso.de" target="_blank"> <object data="files_and_images/Logo-adesso.png" type="image/png" >adesso AG</object></a>:
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  This pattern is valid in XHTML and SpecIF, but not in ReqIF. To conform with the latter, it can be transformed to: <object data="https://adesso.de" ><object data="files_and_images/Logo-adesso.png" type="image/png" >adesso AG</object></object>

## Project Information (SpecIF:Paragraph)
- dcterms:title: Link with an embedded comprehensive object tag
- dcterms:description: A link with a nested object referencing an image like <a href="https://adesso.de"> <object data="files_and_images/Logo-adesso.png" type="image/png" name="adesso AG" /></a>:
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  This pattern is valid in XHTML and SpecIF, but not in ReqIF. To conform with the latter, it can be transformed to: <object data="https://adesso.de" ><object data="files_and_images/Logo-adesso.png" type="image/png" name="adesso AG" /></object>
