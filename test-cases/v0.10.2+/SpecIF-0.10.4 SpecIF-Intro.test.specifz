# SpecIF Intro
- Rights: Creative Commons 4.0 CC BY-SA, https://creativecommons.org/licenses/by-sa/4.0/

## Project Information (SpecIF:Paragraph)
- dcterms:description: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
  This is a small show-case illustrating the basic concepts for documenting business processes and IT. In addition to the original text and diagrams you will find logical relations between the information elements. Most relations are derived automatically from the diagrams; the resulting semantic net lends itself for navigation, search and audit.
  The documentation represents and integrates:
  - Organisation perspective: [[Organization Chart]]
  - Business perspective: [[Business Landscape]] and Business Processes such as [[Process: Invoice Receipt Processing]]
  - Application perspective: [[Application Landscape]]
  - [[Requirements]]
  Integrating the perspectives means to (mostly automatically) tie a semantic net with relations:
  - Diagrams 'show' a model element, thus any element 'knows' on which diagrams it appears,
  - Components 'contain' sub-components,
  - Events 'trigger' activities,
  - Components 'satisfy' a requirement,
  - .. and many more.
  Active hyperlinks make it easy to navigate along the relations. Insight is improved, navigation and audition are made more simple. For more information on the method applied, please refer to Specification Integration Facility (SpecIF), an initiative of the Gesellschaft für Systems Engineering (GfSE).
  If you are using Firefox, Chrome or Edge as a browser, don't hesitate to click on the diagram elements. It will bring you to the next level of detail.
  Stakeholders:
  | Name | Organisation | Telephone | Email |
  | --- | --- | --- | --- |
  | Dr. Oskar v. Dungern | adesso AG |  | oskar.dungern@adesso.de |
  Legend:
  To distinguish their type, element names are preceded by one of the following symbols:
  | ▣ | Plan | A 'Diagram' is a graphical model view with a specific communication purpose, e.g. a business process or system composition. |
  | --- | --- | --- |
  | ■ | Actor (Role, Function) | An 'Actor' is a fundamental model element type representing an active entity, be it an activity, a process step, a function, a system component or a role. |
  | ● | State (Information) | A 'State' is a fundamental model element type representing a passive entity, be it a value, a condition, an information storage or even a physical shape. |
  | ♦ | Event | An 'Event' is a fundamental model element type representing a time reference, a change in condition/value or more generally a synchronisation primitive. |
  | ✶ | Feature | A 'Feature' is an intentional distinguishing characteristic of a system, often a unique selling proposition. |
  | ↯ | Requirement | A 'Requirement' is a singular documented physical and functional need that a particular design, product or process must be able to perform. |
