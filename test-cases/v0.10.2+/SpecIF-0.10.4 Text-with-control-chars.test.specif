# A test with text containing control characters
- Rights: Creative Commons 4.0 CC BY-SA, https://creativecommons.org/licenses/by-sa/4.0/

## SpecIF:Paragraph (SpecIF:Paragraph)
- dcterms:title: Projektinformation
- dcterms:description: Ein Text nach Tabulator mit Umbruch
   und weiteren zwei Umbrüchen

  bevor es hiermit weiter geht.
