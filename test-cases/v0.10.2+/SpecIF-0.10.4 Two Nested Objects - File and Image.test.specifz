# Two nested objects with file and image (project title)
- Rights: Creative Commons 4.0 CC BY-SA, https://creativecommons.org/licenses/by-sa/4.0/

## Project Information (SpecIF:Paragraph)
- dcterms:title: Object with an embedded full object tag pair
- dcterms:description: Two pairs of nested objects follow; the outer has a pdf file, the inner references an icon like <object data="files_and_images/2017-09_GfSE-EMEA-Workshop_SpecIF.pdf" type="application/pdf" ><object data="files_and_images/pdf-icon.png" type="image/png" >2017-09_GfSE-EMEA-Workshop_SpecIF</object></object>:
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  This was the first nested object pair and now comes a single object with tag pair:
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  This pattern is valid in XHTML, SpecIF and ReqIF.
