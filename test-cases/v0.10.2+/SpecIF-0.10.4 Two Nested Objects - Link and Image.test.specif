# Two nested objects with link and image (project title)
- Rights: Creative Commons 4.0 CC BY-SA, https://creativecommons.org/licenses/by-sa/4.0/

## Project Information (SpecIF:Paragraph)
- dcterms:title: Object with an embedded full object tag pair
- dcterms:description: Two pairs of nested objects follow; the outer has a link, the inner references an image like <object data="https://adesso.de" ><object data="files_and_images/Logo-adesso.png" type="image/png" >adesso AG</object></object>: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
  This was the first nested object pair and now comes a second:
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  This pattern is valid in XHTML, SpecIF and ReqIF.
