# A test with missing propertyClass
- Rights: Creative Commons 4.0 CC BY-SA, https://creativecommons.org/licenses/by-sa/4.0/

## Resource title of Text-1 (SpecIF:Paragraph)
- dcterms:title: Title property of Text-1
- dcterms:description: Description of Text-1.

## Resource title of Text-2 (SpecIF:Paragraph)
- dcterms:title: Title property of Text-2
- dcterms:description: Description of Text-2.
  The property class is not defined.

## Resource title of Text-3 (SpecIF:Paragraph)
- dcterms:title: Title property of Text-3
- dcterms:description: Description of Text-3.
