# A test with good 'extends', i.e. type specialisations
- Rights: Creative Commons 4.0 CC BY-SA, https://creativecommons.org/licenses/by-sa/4.0/

## Title 1 (SpecIF:Paragraph)

## Title 2 (SpecIF:Paragraph)
- dcterms:title: Title text 2
- dcterms:description: Formatted description 2

## Title 3 (SpecIF:Paragraph)
- dcterms:title: Title text 3
- dcterms:description: Formatted description 3
- Other property 1: Value of Other-1

## Title 4 (SpecIF:Paragraph)
- dcterms:title: Title text 4
- dcterms:description: Formatted description 4
  Property 'Other-1' is missing, so the property class' title and value are shown.
- Other property 2: Value of Other-2

## Title 5 (SpecIF:Paragraph)
- dcterms:title: Title text 5
- dcterms:description: Formatted description 5
  Properties 'Other-1' and 'Other-2' come in a wrong sequence.
  Title of 'Other-2' is missing, so the property class' title is shown.
- Other property 2: Value of Other-2
- Other property 1: Value of Other-1
