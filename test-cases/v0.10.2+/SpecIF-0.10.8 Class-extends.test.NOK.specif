# A test with good 'extends', i.e. type specialisations
- Rights: Creative Commons 4.0 CC BY-SA, https://creativecommons.org/licenses/by-sa/4.0/

## Title 1 (SpecIF:Paragraph)

## Title 2 (SpecIF:Paragraph)
- dcterms:title: Title text
- dcterms:description: Formatted description

## Title 3 (SpecIF:Paragraph)
- dcterms:title: Title text
- dcterms:description: Formatted description
- SpecIF:Status: 10_initial
