# A test with good 'extends', i.e. type specialisations
- Rights: Creative Commons 4.0 CC BY-SA, https://creativecommons.org/licenses/by-sa/4.0/

## Title 1 (SpecIF:Paragraph)

## Title 2 (SpecIF:Paragraph)
- dcterms:title: Title of Basis Information
- dcterms:description: Formatted Description of Basic Information

## Title 3 (SpecIF:Paragraph)
- dcterms:title: Title of Extended Information
- dcterms:description: Formatted Description of Extended Information
- SpecIF:Status: 10_initial
