# A test with formatted text using markdown (project title
- Rights: Creative Commons 4.0 CC BY-SA, https://creativecommons.org/licenses/by-sa/4.0/

## unordered-list (SpecIF:Paragraph)
- dcterms:title: Text with unordered-list
- dcterms:description: Text before list; there are line-breaks before the list items:
  - first item
  - zweiter **[Punkt (bold)]**
  - troisième élément
  Text after list.
   We do expect that a list is recognized.

## unordered-list (SpecIF:Paragraph)
- dcterms:title: Text with unordered-list
- dcterms:description: Text before list; there are no line-breaks before the list items:- first item - zweiter **[Punkt (bold)]** - troisième élément
  Text after list.
   We do not expect that a list is recognized.

## ordered-list (SpecIF:Paragraph)
- dcterms:title: Text with ordered-list
- dcterms:description: Text before list:
  1. first _{item (italic)}_
  1. zweiter Punkt
  1. troisième élément
  Text after list.

## A test with formatted text using markdown (hierarchy title) (SpecIF:Hierarchy)
- dcterms:title: A test with formatted text (hierarchy property with title 'dcterms:title')
