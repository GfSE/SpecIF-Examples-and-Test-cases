# Semantic Test (2018-05-17)
- Rights: Creative Commons 4.0 CC BY-SA, https://creativecommons.org/licenses/by-sa/4.0/

## Projektinformation (SpecIF:Paragraph)
- dcterms:description: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
  Legende:
  Zur Unterscheidung ihres Typs ist den Elementnamen eines der folgenden Symbole vorangestellt:
  | ▣ | Plan | Ein 'Plan' ist eine graphische Modellsicht zur Vermittlung eines bestimmten Sachverhalts, z.B. ein Geschäftsprozess oder Systemaufbau. |
  | --- | --- | --- |
  | ■ | Akteur (Rolle, Funktion) | Ein 'Akteur' ist ein fundamentaler Modellelement-Typ für ein aktives Objekt, z.B. eine Aktivität, ein Prozess-Schritt, eine Funktion, eine Systemkomponente oder eine Rolle. |
  | ● | Zustand (Information) | Ein 'Zustand' ist ein fundamentaler Modellelement-Typ für ein passives Objekt, z.B. ein Wert, ein Dokument, ein Informationsspeicher oder eine physische Beschaffenheit. |
  | ♦ | Ereignis | Ein 'Ereignis' ist ein fundamentaler Modellelement-Typ für eine zeitliche Referenz, eine Änderung einer Bedingung bzw. eines Zustandes oder generell ein Synchronisations-Mittel. |
  | ✶ | Produktmerkmal | Ein 'Produktmerkmal' ist eine beabsichtigte differenzierende Eigenschaft eines Systems, oft ein Alleinstellungsmerkmal. |
  | ↯ | Anforderung | Eine 'Anforderung' ist ein einzelnes dokumentiertes physisches oder funktionales Bedürfnis, das der betreffende Entwurf, das Produkt oder der Prozess erfüllen muss. |
  | ☛ | Annotation | Eine Interaction-Room 'Annotation' weist auf einen Punkt besonderen Interesses hin. Hierzu gehören Werte, die Kundenbedürfnisse widerspiegeln oder positiven Effekt auf die Ziele der Organisation haben, Produkteigenschaften, deren Umsetzung Nutzen/Aufwand verursacht, und Herausforderungen, die während der Entwicklung zu berücksichtigen sind. |

## Modellelemente (Glossar) (SpecIF:Heading)

## Typ 'Akteur' (SpecIF:Heading)
- dcterms:description: Ein 'Akteur' ist ein fundamentaler Modellelement-Typ für ein aktives Objekt, z.B. eine Aktivität, ein Prozess-Schritt, eine Funktion, eine Systemkomponente oder eine Rolle.

## Typ 'Zustand' (SpecIF:Heading)
- dcterms:description: Ein 'Zustand' ist ein fundamentaler Modellelement-Typ für ein passives Objekt, z.B. ein Wert, ein Dokument, ein Informationsspeicher oder eine physische Beschaffenheit.

## Typ 'Ereignis' (SpecIF:Heading)
- dcterms:description: Ein 'Ereignis' ist ein fundamentaler Modellelement-Typ für eine zeitliche Referenz, eine Änderung einer Bedingung bzw. eines Zustandes oder generell ein Synchronisations-Mittel.

## BPMN (SpecIF:Diagram)
- SpecIF:Diagram: Plan:
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- SpecIF:Notation: BPMN Process Model

## Kommunikation mit Fachobjekten (SpecIF:Diagram)
- SpecIF:Diagram: Plan:
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- SpecIF:Notation: FMC Block Diagram

## Kommunikation ohne Fachobjekte (SpecIF:Diagram)
- SpecIF:Diagram: Plan:
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- SpecIF:Notation: FMC Block Diagram

## Daten-1 (FMC:State)

## Daten-1b (FMC:State)

## Daten-2b (FMC:State)
- dcterms:description: This business data object plays an important role in '[[Kommunikation mit Fachobjekten]]'; therefore it must be implemented early!

## Daten-4b (FMC:State)

## Ende-1 (FMC:Event)

## Fall-a (FMC:State)

## Fall-b (FMC:State)

## Funktion-1 (FMC:Actor)

## Funktion-1b (FMC:Actor)

## Funktion-2 (FMC:Actor)

## Funktion-2b (FMC:Actor)

## Funktion-3 (FMC:Actor)

## Funktion-3b (FMC:Actor)

## Funktion-4 (FMC:Actor)

## Funktion-4b (FMC:Actor)

## Rolle-1 (FMC:Actor)

## Rolle-2 (FMC:Actor)

## Schritt-1 (FMC:Actor)

## Schritt-2a (FMC:Actor)

## Schritt-2b (FMC:Actor)

## Schritt-3 (FMC:Actor)

## Schritt-4 (FMC:Actor)

## Start-2 (FMC:Event)

## Semantic Test (2018-05-17) (SpecIF:Hierarchy)

## Statements
- BPMN SpecIF:shows Daten-1
- BPMN SpecIF:shows Ende-1
- BPMN SpecIF:shows Fall-a
- BPMN SpecIF:shows Fall-b
- BPMN SpecIF:shows Rolle-1
- BPMN SpecIF:shows Rolle-2
- BPMN SpecIF:shows Schritt-1
- BPMN SpecIF:shows Schritt-2a
- BPMN SpecIF:shows Schritt-2b
- BPMN SpecIF:shows Schritt-3
- BPMN SpecIF:shows Schritt-4
- BPMN SpecIF:shows Start-2
- Kommunikation mit Fachobjekten SpecIF:shows Daten-1b
- Kommunikation mit Fachobjekten SpecIF:shows Daten-2b
- Kommunikation mit Fachobjekten SpecIF:shows Daten-4b
- Kommunikation mit Fachobjekten SpecIF:shows Funktion-1b
- Kommunikation mit Fachobjekten SpecIF:shows Funktion-2b
- Kommunikation mit Fachobjekten SpecIF:shows Funktion-3b
- Kommunikation mit Fachobjekten SpecIF:shows Funktion-4b
- Kommunikation ohne Fachobjekte SpecIF:shows Funktion-1
- Kommunikation ohne Fachobjekte SpecIF:shows Funktion-2
- Kommunikation ohne Fachobjekte SpecIF:shows Funktion-3
- Kommunikation ohne Fachobjekte SpecIF:shows Funktion-4
- Schritt-2a SpecIF:precedes Ende-1
- Schritt-2b SpecIF:precedes Ende-1
- Schritt-3 SpecIF:precedes Ende-1
- Schritt-4 SpecIF:precedes Ende-1
- Funktion-2 SpecIF:sendsTo Funktion-1
- Funktion-4 SpecIF:sendsTo Funktion-1
- Funktion-1b SpecIF:writes Daten-1b
- Funktion-1b SpecIF:reads Daten-1b
- Funktion-1b SpecIF:writes Daten-4b
- Funktion-1b SpecIF:reads Daten-4b
- Funktion-1 SpecIF:sendsTo Funktion-2
- Funktion-2b SpecIF:writes Daten-1b
- Funktion-2b SpecIF:reads Daten-1b
- Funktion-2b SpecIF:writes Daten-2b
- Funktion-2 SpecIF:sendsTo Funktion-3
- Funktion-3b SpecIF:reads Daten-2b
- Funktion-1 SpecIF:sendsTo Funktion-4
- Funktion-4b SpecIF:writes Daten-4b
- Funktion-4b SpecIF:reads Daten-4b
- Rolle-1 SpecIF:contains Fall-a
- Rolle-1 SpecIF:contains Fall-b
- Rolle-1 SpecIF:contains Schritt-1
- Rolle-1 SpecIF:contains Schritt-2a
- Rolle-1 SpecIF:contains Schritt-2b
- Rolle-2 SpecIF:contains Ende-1
- Rolle-2 SpecIF:contains Schritt-3
- Rolle-2 SpecIF:contains Schritt-4
- Rolle-2 SpecIF:contains Start-2
- Schritt-2a SpecIF:writes Daten-1
- Schritt-2a SpecIF:reads Daten-1
- Schritt-1 SpecIF:precedes Schritt-2a
- Schritt-3 SpecIF:sendsTo Schritt-2b
- Schritt-1 SpecIF:precedes Schritt-2b
- Schritt-2b SpecIF:sendsTo Schritt-3
- Start-2 SpecIF:precedes Schritt-3
- Schritt-4 SpecIF:writes Daten-1
- Schritt-4 SpecIF:reads Daten-1
- Schritt-3 SpecIF:precedes Schritt-4
