# Text with SVG image (2019-07-18)
- Rights: Creative Commons 4.0 CC BY-SA, https://creativecommons.org/licenses/by-sa/4.0/

## Legend (SpecIF:Diagram)
- SpecIF:Diagram: Some text before the image in it's own paragraph.
  Plan:
  Some text before the image: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Some text after the image, but in the same paragraph.
  Some text after the image in it's own paragraph.
- SpecIF:Notation: FMC Block Diagram

## Text with SVG image (2018-10-09) (SpecIF:Hierarchy)
