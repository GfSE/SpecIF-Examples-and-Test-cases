# A test with hierarchical text
- Rights: Creative Commons 4.0 CC BY-SA, https://creativecommons.org/licenses/by-sa/4.0/

## multiple paragraphs (SpecIF:Paragraph)
- dcterms:title: Text with multiple paragraphs
- dcterms:description: first paragraph, an empty paragraph follows:
  Zweiter Absatz.
  Lorem ipsum dolor sit amet, consetetur sadipscing elitr, sed diam nonumy eirmod tempor invidunt ut labore et dolore magna aliquyam erat, sed diam voluptua. At vero eos et accusam et justo duo dolores et ea rebum. Stet clita kasd gubergren, no sea takimata sanctus est Lorem ipsum dolor sit amet. Lorem ipsum dolor sit amet, consetetur sadipscing elitr, sed diam nonumy eirmod tempor invidunt ut labore et dolore magna aliquyam erat, sed diam voluptua. At vero eos et accusam et justo duo dolores et ea rebum. Stet clita kasd gubergren, no sea takimata sanctus est Lorem ipsum dolor sit amet.
  troisième paragraphe.

## a simple table (SpecIF:Paragraph)
- dcterms:title: Text with a simple table
- dcterms:description:
  | Name | Organisation | Telephone | Email |
  | --- | --- | --- | --- |
  | Dr. Oskar Surname | adesso AG |  | name.surname@adesso.de |

## chapter title first level (SpecIF:Heading)
- dcterms:title: chapter title first level (title property)
- dcterms:description: Some introductory text at first level.

## chapter title second level (SpecIF:Heading)
- dcterms:title: chapter title second level (title property)
- dcterms:description: Some introductory text at second level.

## A test with hierarchical text (hierarchy title) (SpecIF:Hierarchy)
- dcterms:title: A test with hierarchical text (hierarchy property with title 'dcterms:title')
