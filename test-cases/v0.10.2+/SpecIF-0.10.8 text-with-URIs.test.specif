# A test with formatted text
- Rights: Creative Commons 4.0 CC BY-SA, https://creativecommons.org/licenses/by-sa/4.0/

## A text with some URIs to be linkified (resource title) (SpecIF:Paragraph)
- dcterms:description: Line-Break using &#xD;.
References:
- SE: https://ad.sharepoint.com/:w:/r/sites/BFS/_layouts/15/Doc.aspx?sourcedoc=%7B2AF84075-68D8-48A7-A619-FA0C75BFC8D2%7D&file=DE00326686_EB.001.01_DE_Systemarchitektur_PH2.docx&action=default&mobileredirect=true&cid=1ef0db74-0c62-4915-9659-12962ae190cc
- Integrations-Overview: https://ad.sharepoint.com/sites/BFS/Austausch/Forms/AllItems.aspx?id=%2Fsites%2FBFS%2FAustausch%2F007%5FPH%5F20191115%2F05%5FIntegrationen%2FDE00326686%5FEE%2E004%2E01%5FDE%5FAD%5FIntegrations%5FOverview%2D20191115%2Epdf&parent=%2Fsites%2FBFS%2FAustausch%2F007%5FPH%5F20191115%2F05%5FIntegrationen&p=true&originalPath=aHR0cHM6Ly92YXR0ZW5mYWxsLnNoYXJlcG9pbnQuY29tLzpiOi9zL0JGS0FETVMvRVZ2SEFKZkgyMTVEdHRUZ1o5LWM3NG9CVEtnQllnb3NLLW5MTWNHZDExZzNlZz9ydGltZT1xS0xiYU9DVTEwZw
- Infrastructure Solution Design - v1.0 https://ad.sharepoint.com/:w:/r/sites/BFS/Austausch/SB-intern/Dokumente_Arbeitsverzeichnis_alt/004_Architektur/FieldClient_WebDMD%20(incl%202FA)/AD%20-%20Infrastructure%20Solution%20Design%20-%20v1.0.docx?d=w7c76f1f3c3e649efa472bd8e5106c6be&csf=1&web=1&e=4uAyn2

## A text with some URIs to be linkified (resource title) (SpecIF:Paragraph)
- dcterms:description: Line-Break using \n.
  References:
  - SE: https://ad.sharepoint.com/:w:/r/sites/BFS/_layouts/15/Doc.aspx?sourcedoc=%7B2AF84075-68D8-48A7-A619-FA0C75BFC8D2%7D&file=DE00326686_EB.001.01_DE_Systemarchitektur_PH2.docx&action=default&mobileredirect=true&cid=1ef0db74-0c62-4915-9659-12962ae190cc
  - Integrations-Overview: https://ad.sharepoint.com/sites/BFS/Austausch/Forms/AllItems.aspx?id=%2Fsites%2FBFS%2FAustausch%2F007%5FPH%5F20191115%2F05%5FIntegrationen%2FDE00326686%5FEE%2E004%2E01%5FDE%5FAD%5FIntegrations%5FOverview%2D20191115%2Epdf&parent=%2Fsites%2FBFS%2FAustausch%2F007%5FPH%5F20191115%2F05%5FIntegrationen&p=true&originalPath=aHR0cHM6Ly92YXR0ZW5mYWxsLnNoYXJlcG9pbnQuY29tLzpiOi9zL0JGS0FETVMvRVZ2SEFKZkgyMTVEdHRUZ1o5LWM3NG9CVEtnQllnb3NLLW5MTWNHZDExZzNlZz9ydGltZT1xS0xiYU9DVTEwZw
  - Infrastructure Solution Design - v1.0 https://ad.sharepoint.com/:w:/r/sites/BFS/Austausch/SB-intern/Dokumente_Arbeitsverzeichnis_alt/004_Architektur/FieldClient_WebDMD%20(incl%202FA)/AD%20-%20Infrastructure%20Solution%20Design%20-%20v1.0.docx?d=w7c76f1f3c3e649efa472bd8e5106c6be&csf=1&web=1&e=4uAyn2

## A test with URIs (SpecIF:Hierarchy)
