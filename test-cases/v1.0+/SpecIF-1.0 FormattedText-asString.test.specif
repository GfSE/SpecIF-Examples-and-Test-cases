# A test with formatted text in a property with dataType 'xs:string'
- Rights: Creative Commons 4.0 CC BY-SA, https://creativecommons.org/licenses/by-sa/4.0/

## A test with formatted text in a property with dataType 'xs:string' (SpecIF:Hierarchy)
- dcterms:title: A test with formatted text (hierarchy property with title 'dcterms:title')

## Text with a simple table having a thead section (SpecIF:Paragraph)
- dcterms:description:
  | Name | Organisation | Telephone | Email |
  | --- | --- | --- | --- |
  | Oskar Surname | adesso AG |  | oskar.surname@adesso.de |

## Text with a simple table (SpecIF:Paragraph)
- dcterms:description:
  | Name | Organisation | Telephone | Email |
  | --- | --- | --- | --- |
  | Oskar Surname | adesso AG |  | oskar.surname@adesso.de |

## Text with multiple paragraphs (SpecIF:Paragraph)
- dcterms:description: First paragraph, an empty paragraph follows:
  Nächster Absatz.
  Lorem ipsum dolor sit amet, consetetur sadipscing elitr, sed diam nonumy eirmod tempor invidunt ut labore et dolore magna aliquyam erat, sed diam voluptua. At vero eos et accusam et justo duo dolores et ea rebum. Stet clita kasd gubergren, no sea takimata sanctus est Lorem ipsum dolor sit amet. Lorem ipsum dolor sit amet, consetetur sadipscing elitr, sed diam nonumy eirmod tempor invidunt ut labore et dolore magna aliquyam erat, sed diam voluptua. At vero eos et accusam et justo duo dolores et ea rebum. Stet clita kasd gubergren,
  no sea takimata sanctus est Lorem ipsum dolor sit amet.
  A hyperlink without <a> tag: https://specif.de/apps/edit#import=../examples/Dimmer.specifz
  Dernier paragraphe.

## Text with nested ordered and unordered list (SpecIF:Paragraph)
- dcterms:description: Text before list:
  1. first {item (italic)}
  2. zweiter Punkt
  3. troisième élément
  4. Subordinated unordered list:
  - first unordered sub-item
  - zweiter [Unterpunkt (bold)]
  - troisième élément subordonné
  The end.

## Text with ordered list (SpecIF:Paragraph)
- dcterms:description: Text before orddered list:
  1. first {item (italic)}
  2. zweiter Punkt
  3. troisième élément
  Text after numbered list. The next is an unordered list:
  - first item
  - zweiter [Punkt (bold)]
  - troisième élément
  The end.

## Text with ordered list (SpecIF:Paragraph)
- dcterms:description: Text before list:
  1. first {item (italic)}
  2. zweiter Punkt
  3. troisième élément
  Text between two lists. The next list should start with '1' again.
  1. first {item (italic)}
  2. zweiter Punkt
  3. troisième élément
  4. next
  5. next
  6. next
  7. next
  8. next
  9. next
  10. next
  11. next
  Text after list.

## Text with unordered list (SpecIF:Paragraph)
- dcterms:description: Text before list:
  - first item
  - zweiter [Punkt (bold)]
  - troisième élément
  Text after list.

## Text with some character formatting, colors as RGB Hex like '#008000' (SpecIF:Paragraph)
- dcterms:description: Lorem {ipsum (bold)} dolor [sit (italic)] amet, {consetetur sadipscing (emphasized)}[elitr (span #FF0000)], sed diam {nonumy (span #0000FF, bold)} [eirmod{tempor (span #008000)}(emphasized)], no {[sea (bold)]takimata (emphasized)} Mojito!.

## Text with some special characters (title property) (SpecIF:Paragraph)
- dcterms:description: I am < 2m tall and my weight is >20kg.

## Text with some character formatting, colors as HTML literal like 'green' (SpecIF:Paragraph)
- dcterms:description: Lorem {ipsum (bold)} dolor [sit (italic)] amet, {consetetur sadipscing (emphasized)}[elitr (span red)], sed diam {nonumy (span blue, bold)} [eirmod{tempor (span green)}(emphasized)], no {[sea (bold)]takimata (emphasized)} Mojito!
