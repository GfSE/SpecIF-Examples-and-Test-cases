# A test with formatted text using markdown
- Rights: Creative Commons 4.0 CC BY-SA, https://creativecommons.org/licenses/by-sa/4.0/

## A test with formatted text in a property with dataType 'xs:string' (SpecIF:Hierarchy)
- dcterms:title: A test with formatted text (hierarchy property with title 'dcterms:title')

## Text with a simple table (SpecIF:Paragraph)
- dcterms:description:
  | Name | Organisation | Telephone | Email |
  |---|---|---|---|
  | Oskar Surname | enso managers GmbH | | od@enso-managers.de |

## Text with multiple paragraphs and sub-titles (SpecIF:Paragraph)
- dcterms:title: Text with multiple paragraphs
- dcterms:description: First paragraph. #### Ein Untertitel vierte Ebene Lorem ipsum dolor sit amet, __consetetur sadipscing__ elitr, sed diam nonumy eirmod tempor invidunt ut labore et dolore magna aliquyam erat, sed diam voluptua. At vero eos et accusam et justo duo dolores et ea rebum. Stet clita kasd gubergren, no sea takimata sanctus est Lorem ipsum dolor sit amet. Lorem ipsum dolor sit amet, consetetur sadipscing elitr, sed diam nonumy eirmod tempor invidunt ut labore et dolore magna aliquyam erat, sed diam voluptua. At vero eos et accusam et justo duo dolores et ea rebum. Stet clita kasd gubergren,
  no sea takimata sanctus est Lorem ipsum dolor sit amet. A _hyperlink_ without <a> tag: https://specif.de/apps/edit#import=../examples/Dimmer.specifz Dernier paragraphe.

## Text with multiple paragraphs and a plain URL (SpecIF:Paragraph)
- dcterms:title: Text with multiple paragraphs
- dcterms:description: First paragraph. Nächster Absatz. Lorem ipsum dolor sit amet, consetetur sadipscing elitr, sed diam nonumy eirmod tempor invidunt ut labore et dolore magna aliquyam erat, sed diam voluptua. At vero eos et accusam et justo duo dolores et ea rebum. Stet clita kasd gubergren, no sea takimata sanctus est Lorem ipsum dolor sit amet. Lorem ipsum dolor sit amet, consetetur sadipscing elitr, sed diam nonumy eirmod tempor invidunt ut labore et dolore magna aliquyam erat, sed diam voluptua. At vero eos et accusam et justo duo dolores et ea rebum. Stet clita kasd gubergren,
  no sea takimata sanctus est Lorem ipsum dolor sit amet. A _hyperlink_ without <a> tag: https://specif.de/apps/edit#import=../examples/Dimmer.specifz Dernier paragraphe.

## Text with ordered and unordered list (SpecIF:Paragraph)
- dcterms:description: Text before ordered list:
  1. First _{item (italic)}_
  1. Zweiter Punkt
  1. Troisième élément

  Text after numbered list. The next is an unordered list:
  - First item
  - Zweiter __[Punkt (bold)]__
  - Troisième élément

  The end.

## Text with two ordered lists (SpecIF:Paragraph)
- dcterms:description: Text before list:
  1. First _{item (italic)}_
  1. Zweiter Punkt
  1. Troisième élément

   Text between two lists. The next list should start with '1' again.
  1. First item
  1. Zweiter Punkt
  1. Troisième élément
  1. Next
  1. Next
  1. Letzter Aufzählungspunkt

  Text after list.

## Text with nested unordered lists (SpecIF:Paragraph)
- dcterms:description: Text before list:
  - First item
  - Zweiter __[Punkt (bold)]__
      - 2.1
      - 2.2
  - Troisième élément

  Text after list.

## Text with unordered list (SpecIF:Paragraph)
- dcterms:description: Text before list:
  - First item
  - Zweiter __[Punkt (bold)]__
  - Troisième élément
  Deuxième ligne.

  Text after list.

## Text with some character formatting, colors as RGB Hex like '#008000' (SpecIF:Paragraph)
- dcterms:description: Lorem **{ipsum (bold)}** dolor *[sit (italic)]* amet, *{consetetur sadipscing (emphasized)}*[elitr (span #FF0000)], sed diam **{nonumy (span #0000FF, bold)}** *[eirmod{tempor (span #008000)}(emphasized)]*, no ***{[sea (bold)]*** *takimata (emphasized)}* Mojito!.

## Text with some special characters (title property) (SpecIF:Paragraph)
- dcterms:description: I am < 2m tall and my weight is >20kg.

## Text with some character formatting, colors as HTML literal like 'green' (SpecIF:Paragraph)
- dcterms:description: Lorem __{ipsum (bold)}__ dolor _[sit (italic)]_ amet, _{consetetur sadipscing (emphasized)}_[elitr (span red)], sed diam __{nonumy (span blue, bold)}__ _[eirmod{tempor (span green)}(emphasized)]_, no ***{[sea (bold)]*** *takimata (emphasized)}* Mojito!
