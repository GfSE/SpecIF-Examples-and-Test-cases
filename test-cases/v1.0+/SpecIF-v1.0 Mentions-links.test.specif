# Example 'Integrated Process and IT Documentation' (2021-01-27)
This sample project illustrates the basic concepts of the modelling of business processes and IT, but is neither complete nor representative regarding the content.  The specification integrates and represents:• organisational view: organigram• business view:  business landscape and business data modell• application view: application landscape
- Rights: Creative Commons 4.0 CC BY-SA, https://creativecommons.org/licenses/by-sa/4.0/

## SAP FI (FMC:Actor)
- dcterms:description: SAP Financial Accounting System, which is used for the administration of [[invoice]]s and cash flow among others.

## SAP SCM (FMC:Actor)
- dcterms:description: SAP Supply Chain Management System, which is used for the administration of [[supplier]] data and [[order]]s.

## Invoice (FMC:State)
- dcterms:description: An invoice is a document which contains a detailed list of the monetary claim of a supplier for delivered goods or services. It contains all required data for the administration of invoices. Managed by [[SAP FI]].

## Order (FMC:State)
- dcterms:description: Is an instruction to the supplier to deliver a specified list of articles on a specified date to a specified address. All data necessary for the administration of the order are collected.
