# A test with various formatted and unformatted titles
- Rights: Creative Commons 4.0 CC BY-SA, https://creativecommons.org/licenses/by-sa/4.0/

## R-1: A resource title as plain text, wobei kleiner < größer. (SpecIF:Hierarchy)

## R-2: A resource title as plain text. (SpecIF:Hierarchy)
- dcterms:title: R-2: A property with title 'dcterms:title' and dataType 'xs:string' as plain text.

## R-3: A resource title as plain text. (SpecIF:Hierarchy)
- dcterms:title: R-3: kleiner < größer.

## R-4: A resource title as plain text. (SpecIF:Hierarchy)
- dcterms:title: R-4: kleiner < größer.

## R-5: A resource title as plain text. (SpecIF:Hierarchy)
- dcterms:title: R-5: Minimum button size is < than the maximum size.
