# A resource with properties covering all dataTypes
Excerpt from example 'Dimmer'.
- Rights: Creative Commons 4.0 CC BY-SA, https://creativecommons.org/licenses/by-sa/4.0/

## Requirements (SpecIF:Heading)

## Dim an electric load (IREB:Requirement)
- dcterms:identifier: REQ_014
- dcterms:description: The user can set the intensity level of an electric load such as a light bulb. Pressing a button 'up' or 'down', the intensity is increased or decreased following a quasi-stepless ramp.
- SpecIF:Priority: Rather Low
- Importance: 101
- Discipline: Mechanics, Software
- SpecIF:DueDate: 2021-08-30T18:00:00Z

## Example for multiple text-values, one of them in two languages. (SpecIF:Heading)
- dcterms:description: First value: Unformatted text A in a single language.,
  Second value: XHTML-formatted Text B in English.
- SpecIF:Reference: https://specif.de, http://github.com/GfSE/
