# SNB SNAP - Projektprozesse (2020-06-16)
Die vernetzte Dokumentation des Projekts SNAP TP4 Projektprozesse. Es werden ausführbare Geschäftsprozesse modelliert und ergänzend die Perspektiven Organigramm, Applikations-Landkarte (Bebauungsplan) und Fachobjekt-Landkarte (Datenmodell) dargestellt.Alle Modellelemente sind, sofern sie einen identischen Namen tragen, konsolidiert. Es kann geprüft werden, auf welchen Modelldiagrammen sie erscheinen und welche Beziehungen sie zu anderen Modellelementen aufweisen. Beispielsweise lässt sich prüfen, welche Fachobjekte von welchen Prozess-Schritten erzeugt/modifiziert oder als Eingangsinformation benötigt werden. Die Modellelemente sind im letzten Kapitel „Glossar“ alphabetisch aufgeführt.
- Rights: Creative Commons 4.0 CC BY-SA, https://creativecommons.org/licenses/by-sa/4.0/

## Projektinformation (SpecIF:Heading)
- dcterms:description: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
  Die vernetzte Dokumentation des Projekts SNAP TP4 Projektprozesse. Es werden ausführbare Geschäftsprozesse modelliert und ergänzend die Perspektiven Organigramm, Applikations-Landkarte (Bebauungsplan) und Fachobjekt-Landkarte (Datenmodell) dargestellt.
  Alle Modellelemente sind, sofern sie einen identischen Namen tragen, konsolidiert. Es kann geprüft werden, auf welchen Modelldiagrammen sie erscheinen und welche Beziehungen sie zu anderen Modellelementen aufweisen. Beispielsweise lässt sich prüfen, welche Fachobjekte von welchen Prozess-Schritten erzeugt/modifiziert oder als Eingangsinformation benötigt werden.
  Die Modellelemente sind im letzten Kapitel „Glossar“ alphabetisch aufgeführt.
  Projektbeteiligte:
  | Name | Organisation | Telefon | Email |
  | --- | --- | --- | --- |
  | Dr. Andreas Raab | adesso SE |  | andreas.raab@adesso.de |
  | Dr. Oskar von Dungern | adesso SE | +49 162 2808 376 | oskar.dungern@adesso.de |
  | Julia Kohls | adesso SE |  | julia.kohls@adesso.de |
  | Sebastian Wiemer | adesso SE |  | sebastian.wiemer@adesso.de |
  | Tobias Rook | adesso SE |  | tobias.rook@adesso.de |
  Legende:
  Zur Unterscheidung ihres Typs ist den Elementnamen eines der folgenden Symbole vorangestellt:
  | ▣ | Plan | Ein 'Plan' ist eine graphische Modellsicht zur Vermittlung eines bestimmten Sachverhalts, z.B. ein Geschäftsprozess oder Systemaufbau. |
  | --- | --- | --- |
  | ■ | Akteur (Rolle, Funktion) | Ein 'Akteur' ist ein fundamentaler Modellelement-Typ für ein aktives Objekt, z.B. eine Aktivität, ein Prozess-Schritt, eine Funktion, eine Systemkomponente oder eine Rolle. |
  | ● | Zustand (Information) | Ein 'Zustand' ist ein fundamentaler Modellelement-Typ für ein passives Objekt, z.B. ein Wert, ein Dokument, ein Informationsspeicher oder eine physische Beschaffenheit. |
  | ♦ | Ereignis | Ein 'Ereignis' ist ein fundamentaler Modellelement-Typ für eine zeitliche Referenz, eine Änderung einer Bedingung bzw. eines Zustandes oder generell ein Synchronisations-Mittel. |
  | ✶ | Produktmerkmal | Ein 'Produktmerkmal' ist eine beabsichtigte differenzierende Eigenschaft eines Systems, oft ein Alleinstellungsmerkmal. |
  | ↯ | Anforderung | Eine 'Anforderung' ist ein einzelnes dokumentiertes physisches oder funktionales Bedürfnis, das der betreffende Entwurf, das Produkt oder der Prozess erfüllen muss. |
  | ☛ | Annotation | Eine Interaction-Room 'Annotation' weist auf einen Punkt besonderen Interesses hin. Hierzu gehören Werte, die Kundenbedürfnisse widerspiegeln oder positiven Effekt auf die Ziele der Organisation haben, Produkteigenschaften, deren Umsetzung Nutzen/Aufwand verursacht, und Herausforderungen, die während der Entwicklung zu berücksichtigen sind. |

## Landkarten (SpecIF:Heading)
- dcterms:description: Aus den originalen Wandtafel-Skizzen des IR-Workshops entwickelte Landkarten in fachlicher Notation und nach Interesse detailliert.

## Modellelemente (Glossar) (SpecIF:Heading)
- dcterms:type: SpecIF:Glossary

## Typ 'Akteur' (SpecIF:Heading)
- dcterms:description: Ein 'Akteur' ist ein fundamentaler Modellelement-Typ für ein aktives Objekt, z.B. eine Aktivität, ein Prozess-Schritt, eine Funktion, eine Systemkomponente oder eine Rolle.

## Typ 'Zustand' (SpecIF:Heading)
- dcterms:description: Ein 'Zustand' ist ein fundamentaler Modellelement-Typ für ein passives Objekt, z.B. ein Wert, ein Dokument, ein Informationsspeicher oder eine physische Beschaffenheit.

## Typ 'Ereignis' (SpecIF:Heading)
- dcterms:description: Ein 'Ereignis' ist ein fundamentaler Modellelement-Typ für eine zeitliche Referenz, eine Änderung einer Bedingung bzw. eines Zustandes oder generell ein Synchronisations-Mittel.

## Organigramm SNB (SpecIF:Diagram)
- SpecIF:Diagram: Plan:
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- SpecIF:Notation: Organization Chart

## SNAP Applikations-Landkarte (Vorlage SNB) (SpecIF:Diagram)
- dcterms:description: Die Landkarte der beteiligten IT-Applikationen mit ihren Schnittstellen und den ausgetauschten Fachobjekten.
- SpecIF:Diagram: Plan:
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- SpecIF:Notation: FMC Block Diagram
- Typ: System-Integration

## Applikations-Landkarte (SpecIF:Diagram)
- dcterms:description: Hier werden alle Applikationen dokumentiert, welche im Zuge der Prozessdetaillierung in Interaction-Room Workshops identifiziert werden konnten und sich in den aktuell aufgenommenen Prozessdiagrammen wiederfinden.
  Hierzu gehören eigenveranlasste Einzelprojekte der Hochspannung (EP_EV_HS) und kundenveranlasste Sammelprojekte in der Mittel- und Niederspannung (SP_KV_MSNS).
- SpecIF:Diagram: Plan:
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- SpecIF:Notation: FMC Block Diagram
- Typ: System-Integration

## AVA-Applikationen (IST) (SpecIF:Diagram)
- dcterms:description: Aktuell bei SNB im Einsatz befindliche Software-Applikationen für die Ausschreibung, Vergabe und Abrechnung (AVA) von Bauvorhaben.
- SpecIF:Diagram: Plan:
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- SpecIF:Notation: FMC Block Diagram
- Typ: System-Integration

## AVA-Applikation (Referenz) (SpecIF:Diagram)
- dcterms:description: Diese Darstellung zeigt eine industrie-übliche Installation einer Software-Applikation zur Ausschreibung, Vergabe und Abrechnung (AVA) von Bauprojekten. Sie dient als Referenz im Rahmen der Planung der SNAP Projektprozesse.
- SpecIF:Diagram: Plan:
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- SpecIF:Notation: FMC Block Diagram
- Typ: System-Integration

## Applikations-Landkarte (Interaction Room - zu klären) (SpecIF:Diagram)
- dcterms:description: Hier werden alle Applikationen dokumentiert, welche im Zuge der Prozessdetaillierung in Interaction-Room Workshops identifiziert werden konnten, jedoch bisher in keinem Prozessschritt erfasst wurden und zur weiteren Klärung ausstehen
- SpecIF:Diagram: Plan:
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- SpecIF:Notation: FMC Block Diagram
- Typ: System-Integration

## EP_EV_HS_Fachobjekte (SpecIF:Diagram)
- dcterms:description: Hier werden die Fachobjekte für eigenveranlasste Einzelprojekte in der Hochspannung und ihre Beziehungen in Form eines UML-Klassendiagramms dargestellt.
- SpecIF:Diagram: Plan:
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- SpecIF:Notation: UML Class Diagram
- Typ: Fachobjekte

## SP_KV_MSNS_Fachobjekte (SpecIF:Diagram)
- SpecIF:Diagram: Plan:
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- SpecIF:Notation: UML Class Diagram
- Typ: Fachobjekte

## Abnahmeprotokoll (FMC:State)
- dcterms:description: + Einbehalte
  + Termine
  + Vertragsdaten
  + Gewährleistungszeiträume
  + etc.
- dcterms:type: BPMN:dataObject

## Abrechnung (FMC:Actor)
- dcterms:description: Modul einer Software zur Ausschreibung, Vergabe und Abrechnung (AVA) von Bauvorhaben.

## Abrechnungs-Daten (GAEB) (FMC:State)

## Abstimmungsprotokoll [AM] (FMC:State)
- dcterms:description: Offene Punkte auf Basis der KUSS-Analyse
- dcterms:type: BPMN:dataObject

## ADMS (FMC:Actor)
- dcterms:description: Advanced Distribution Management System (ADMS)

## Alkis (FMC:Actor)

## Angebots-Daten (GAEB) (FMC:State)

## Angebots-Erstellung (FMC:Actor)

## Asset Management (DG-AM) (FMC:Actor)

## Asset Owner Strategy & Business Develop. (DG-DA) (FMC:Actor)

## Assets (DG-A) (FMC:Actor)

## Ausführung (FMC:Actor)

## Ausführungsplan (FMC:State)

## Ausführungsplan [erweitert] (FMC:State)
- dcterms:description: * Zeichnung/en (Visio, AutoCAD)
  * NIS (Planebene)
  + Kostenberechnung (DIN276)
- dcterms:type: BPMN:dataObject

## Ausführungsplan [initial] (FMC:State)
- dcterms:description: + Zeichnung/en (Visio, AutoCAD)
  + NIS (Planebene)
- dcterms:type: BPMN:dataObject

## Ausschreibung (FMC:Actor)
- dcterms:description: Modul einer Software zur Ausschreibung, Vergabe und Abrechnung (AVA) von Bauvorhaben.

## Ausschreibungsunterlagen (FMC:State)
- dcterms:description: Finale verbale Beschreibung dessen was ein AN zu erbringen hat.

  Technischer Teil:
  + Leistungsbeschreibung pro Teilprojekt und Vergabeeinheit (FINAL)
  + Anlagen aus der Feinplanung

  Fachobjekt Vertrag:
  + Grobterminplan
  + Zahlplan
- dcterms:type: BPMN:dataStore

## AutoCAD (FMC:Actor)

## AVA (FMC:Actor)
- dcterms:description: Applikation: Abrechnung, Vergabe, Ausschreibung
  EIN.AVA - Felix, iTWO, BauSU in California Pro
  Leistungskatalog:
  Katalog aller definierten Leistungspositionen aus denen sich dann, wie aus einem Baukasten, alle möglichen Konstellationen zusammensetzen lassen. Derzeit effektiv nur für MuF genutzt.
  Die Preise, die für die Leistungspositionen verwendet werden sollen/können, basieren auf Informationen aus vergangen Projekten. Hier können Mittelwerte und andere Verfahren angewandt werden um diese für neue Projekte anzuwenden. Der Preis einer bestimmten Leistung kann also hier global für alle zukünftigen Kalkulationen angepasst werden. Ähnlich funktioniert dies im Eigenleistungskatalog.
  Leistungsverzeichnis:
  Ein Verzeichnis aller Leistungspositionen die den Inhalt des Projekts beschreibt. Dabei wird der Fokus aktuell auf die Material und Fremdleistungen (MuF) gelegt. Es können damit aber im Prinzip alle Arten von Leistungen kalkuliert werden.
  - Abrufe
  - Typicals

## Bauakte (FMC:State)
- dcterms:description: * Anschlussskizze (Visio, AutoCAD)
  * Bauzaun (NiS)
  * Plan = Netzkonzept (Kabel, Gebäude, Straßen)
  * Netzaufträge koordinieren
  * Maßnahmenempfehlungen einfließen lassen
  * FM-Konzept
  * Kostenberechnung (DIN 276)
  * Mitnahmen (Fernsteuerung/Automation)
  * Baufreigabe
  * Kundenpläne

  + Genehmigungsplan
  + Leitungsauskünfte und Genehmigungen
  + Ausführungsplan
  + Vertrag/Verträge mit AN
- dcterms:type: BPMN:dataObject

## Bauakte [abgeschlossen] (FMC:State)
- dcterms:type: BPMN:dataObject

## Bauakte [angenommen] (FMC:State)
- dcterms:type: BPMN:dataObject

## Bauakte [bemängelt] (FMC:State)
- dcterms:type: BPMN:dataObject

## Bauakte [final_geprüft] (FMC:State)
- dcterms:type: BPMN:dataObject

## Baufreigabe (FMC:State)
- dcterms:type: BPMN:dataObject

## Baustellendokumentation (FMC:State)

## Baustellendokumentation [erstellt] (FMC:State)
- dcterms:description: + Schaltungsbücher
  + Masterpläne
  + Werk- und Montagepläne
  + Ausführungspläne
- dcterms:type: BPMN:dataObject

## Baustellendokumentation [kommentiert] (FMC:State)
- dcterms:description: * Schaltungsbücher
  * Masterpläne
  * Werk- und Montagepläne
  * Ausführungspläne
  + Kommentare
- dcterms:type: BPMN:dataObject

## BauSU (FMC:Actor)
- dcterms:description: AVA-Anwendung - Berlin Licht
  In der Öffentlichen Beleuchtung wird BauSU für das Erstellen von Angeboten und zur Abrechnung genutzt.
  Baumanagement macht mit BauSU Angebote und Abrechnungen für...
  - Arbeiten an Beleuchtungsanlagen bei Baumaßnahmen z.B. Wasserbetriebe
  - Schäden (Unfall)
  - Weihnachtsbeleuchtung
  - Neuer Fußgängerüberweg
  (alles Projekte, bei denen Jahresverträge bestehen)

## Bauunternehmen (FMC:Actor)

## Beauftr. Ü. (FMC:Actor)

## Beauftragung Kunde (FMC:State)
- dcterms:type: BPMN:dataObject

## Berlin Licht Management (DG-AL) (FMC:Actor)

## Betriebsmitteldaten (FMC:State)
- dcterms:description: Excel mit Informationen zu den Betriebsmitteln von Externen
- dcterms:type: BPMN:dataObject

## BU Distribution Germany (DG) (FMC:Actor)

## Budgetentscheidung (FMC:State)
- dcterms:type: BPMN:dataObject

## Budgetforderung (FMC:State)
- dcterms:type: BPMN:dataObject

## Business & Project Controlling (DG-CC) (FMC:Actor)

## Business Administration (DG-CB) (FMC:Actor)

## Business Control (DG-C) (FMC:Actor)

## CAD Hoch/Tiefbau (FMC:Actor)
- dcterms:description: Computer-Aided-Design (CAD) für Hoch-und Tiefbau.

## Cal.pro (FMC:Actor)
- dcterms:description: California PRO, ein 'AVA' Software-Produkt zur Ausschreibung, Vergabe und Abrechnung von Bauvorhaben.

## California.pro (FMC:Actor)

## CaSuP (FMC:Actor)
- dcterms:description: Vattenfall Durchschnittsbildung (CaSuP).

## Claim Settlement (DG-CS) (FMC:Actor)

## CosyNet (FMC:Actor)

## Customer & Market Relations (DG-R) (FMC:Actor)

## Customer Management (DG-RR) (FMC:Actor)

## Diagnose-Tool MS-Kabel (FMC:Actor)
- dcterms:description: Hr. Eisenmann

## Dienstleister-Portal (FMC:Actor)

## Division Management (DG-LM) (FMC:Actor)

## DMS (FMC:Actor)
- dcterms:description: Zentrales Dokumenten-Archiv

## eBASE (FMC:Actor)

## Eckterminplan [inkl. Beschaffungsprozess] (FMC:State)
- dcterms:description: + Bauabschnitte
  + Meilensteine


  Der vom Asset Management erhaltene Phasenplan wird um Bauabschnitte untersetzt und Meilensteine ergänzt.
- dcterms:type: BPMN:dataObject

## ECM (Doxis) (FMC:Actor)

## Enddokumentation (FMC:State)
- dcterms:type: BPMN:dataObject

## Entscheidungsvorlage je Variante (Projektsteckbrief) (FMC:State)
- dcterms:description: Powerpoint mit wesentlichen Projektparametern
- dcterms:type: BPMN:dataObject

## EP_EV_HS (FMC:Actor)

## EP_EV_HS (FMC:State)
- dcterms:description: Einzelprojekt_Eigenveranlasst_Hochspannung

## ERP (FMC:Actor)
- dcterms:description: Software des Enterprise Resource Planning (ERP).

## Felix (FMC:Actor)
- dcterms:description: Felix ist eine AVA-Anwendung der Bereiche Mittel-/Niederspannung und des Bereichs Hochspannung Kabelbau.
  Felix in der Mittel-/Niederspannung:
  - Kalkulieren von Bauvorhaben mit Unterstützung von Kalkulationsmodellen
  - Beauftragung von Vertragsfirmen auf Basis gülziger Kontrakte
  - Prozentuale Verteilung der Kosten (Multikontierung)
  - Erstellen von Kalkulationen für Ausschreibungen und Beauftragung von Vertragsfirmen mit autom. Erzeugung der Banf und Bestellung im SAP
  - Kalkulation von Bauvorhaben durch ext. Ingenieurdienstleister (Fremd-Kalk)
  Felix in der Hochspannung Kabelbau:
  - Pflege von Leistungsverzeichnissen
  - Pflege der Vertragspreise
  - Einspielen von .csv (Mengen) Datei zur Kostenermittlung
  - Erstellung von Baustellenabrechnungen

## FFM (FMC:Actor)
- dcterms:description: Fremdfirmenmanagement

## Field Service Metering (DG-MM) (FMC:Actor)

## Finanzdaten (FMC:State)

## Genehmigungen/Leitungsauskünfte (FMC:State)
- dcterms:type: BPMN:dataObject

## Genehmigungsplan (FMC:State)
- dcterms:description: + Zeichnungen im Einstrichverfahren
- dcterms:type: BPMN:dataObject

## Geräte-Management (FMC:Actor)
- dcterms:description: SNB Modul in SAP-Umgebung

## Gesamtkapazitätsplanung je Gruppe (FMC:State)
- dcterms:description: Abgestimmte & konsolidierte Kapazitätsplanung.
  - personenscharf
- dcterms:type: BPMN:dataStore

## Gesamtkapazitätsplanung Unternehmen (FMC:State)

## GM (FMC:Actor)

## Grid Operation (DG-AG) (FMC:Actor)

## Grobterminplan (FMC:State)
- dcterms:type: BPMN:dataObject

## HAM (FMC:Actor)
- dcterms:description: Hausanschluss-Management, SNB Modul in SAP-Umgebung.

## High Voltage (DG-V) (FMC:Actor)

## High Voltage Plant Construction (DG-VV) (FMC:Actor)

## HR & Management Systems (DG-H) (FMC:Actor)

## HSSE & Management Systems (DG-HS) (FMC:Actor)

## infreSt (FMC:Actor)

## IT & Data Management (DG-DI) (FMC:Actor)

## iTWO (FMC:Actor)
- dcterms:description: AVA-Anwendung für Hochspannung Anlagenbau (Umspannwerke)
  - Erstellung und Pflege von Leistungsverzeichnissen
  - Angebots- und Vergabeprozess mit dem Einkauf
  - Erstellung und Pflege von Vorlageprojekten (Typicals)
  - Kalkulation von UW-Projekten auf Grundlage von Vorlageprojekten
  - Kosten- und Projektdatenbank
  - Projektreview

## Kalk.-Blatt (FMC:Actor)

## Kalkulation (EIN.AVA) (FMC:Actor)

## Kalkulations-Tool (FMC:Actor)
- dcterms:description: der HS

## Kundenanfrage (FMC:State)

## Kundenanfrage [bewertet Berater] (FMC:State)
- dcterms:description: Enthält:
  * Leistungsanfrage
  * Geräte
  * Grundpläne
  * Leistungsbilanz (Datenblätter)
  * Lageplan
  * Anschlusspunkt
  * Adresse
  * HA-Skizzen (optional)
  * Kundenpläne
  + Bewertung
- dcterms:type: BPMN:dataObject

## Kundenanfrage [bewertet Konzeption] (FMC:State)
- dcterms:description: * Leistungsanfrage
  * Geräte
  * Grundpläne
  * Leistungsbilanz (Datenblätter)
  * Lageplan
  * Anschlusspunkt
  * Adresse
  * HA-Skizzen (optional)
  * Kundenpläne
  + Bewertung
- dcterms:type: BPMN:dataObject

## Kundenanfrage [initial] (FMC:State)
- dcterms:description: Enthält:
  * Leistungsanfrage
  * Geräte
  * Grundpläne
  * Leistungsbilanz (Datenblätter)
  * Lageplan
  * Anschlusspunkt
  * Adresse
  * HA-Skizzen (optional)
- dcterms:type: BPMN:dataObject

## Kundenanfrage [technisch geprüft] (FMC:State)
- dcterms:description: Enthält:
  * Leistungsanfrage
  * Geräte
  * Grundpläne
  * Leistungsbilanz (Datenblätter)
  * Lageplan
  * Anschlusspunkt
  * Adresse
  * HA-Skizzen (optional)
  * Kundenpläne
  + Bewertung
- dcterms:type: BPMN:dataObject

## Kundenangebot (FMC:State)
- dcterms:description: + Anschlusstermin
  + Baufreigabe (inkl. Kundenstammdaten)
  + HA-Skizzen
  + etc.
- dcterms:type: BPMN:dataObject

## Langfristplanung (FMC:State)
- dcterms:description: + aktualisierte Kalkulation
  + "Technischer Netzbedarf" berücksichtigt


  UPDATE:
  + aktualisieren des Typicals (lokal für dieses Projekt, Aktualisierung über Kopien - aber die Verknüpfung bleibt bestehen, so dass weitere Aktualisierungen möglich sind)
- dcterms:type: BPMN:dataObject

## Ledan (FMC:Actor)

## Leistungs-Verzeichnis (GAEB) (FMC:State)

## Leistungsbestätigungs-Dokumente (FMC:State)
- dcterms:description: + Abnahmeprotokolle
  + Aufmaße
  + sonstige Dokumente (definiert im Vertrag)
- dcterms:type: BPMN:dataObject

## Leistungserfassungsblatt (FMC:State)
- dcterms:description: Leistungserfassungsblatt Auftragnehmer
- dcterms:type: BPMN:dataObject

## Leistungserfassungsblatt [bestätigt] (FMC:State)
- dcterms:description: Die Bestätigung der LEBs löst in SAP eine Gutschrift aus. Dies erfolgt automatisch im Sub-Ledger-Prozess.
- dcterms:type: BPMN:dataObject

## LiveLink (FMC:Actor)

## Management Board Coordination (DG-DK) (FMC:Actor)

## Market Partner Service (DG-RP) (FMC:Actor)

## Maßnahmenempfehlungs-Liste (FMC:State)
- dcterms:description: - relevant für alle
- dcterms:type: BPMN:dataStore

## Medium & Low Voltage (DG-L) (FMC:Actor)

## Metering (DG-M) (FMC:Actor)

## MoNIS (FMC:Actor)

## Montageauftrag [erteilt] (FMC:State)
- dcterms:type: BPMN:dataObject

## MS Project (FMC:Actor)
- dcterms:description: Netzplan/Grobterminplan:
  Gliedert mindestens die Schnittstellen verschiedener Vertragspartner (Auftragnehmer), so dass die vertragsrelevanten Lieferobjekte sowohl des AG als auch aller AN eindeutig zugeordnet sind. Die Übergabepunkte bilden die Basis für die Vertragspönalen zu den jeweiligen AN um keine Verträge des AG zu anderen AN zu verletzen.
  Der Grobterminplan zeigt also die zeitlichen Rahmen aller Vertragspartner und deren Abhängigkeiten an und ist damit die Basis für die Verträge mit den Auftragnehmern. Die Untersetzung unterhalb dieser Rahmen kann zur Plausibilisierung erfolgen muss aber letztlich in der Verantwortung des jeweiligen Vertragspartners erfolgen.
  Ein Netzplan ist die grafische Darstellung der Abhängigkeit aller Vorgänge im Terminplan. (Vorgänger-Nachfolger-Beziehungen)
  PS: Vorgang und Arbeitspaket haben keine 1:1 Beziehung. Ein Vorgang kann aus mehreren zeitlich gleich gelagerten Arbeitspaketen summiert sein. Wenn zum Beispiel ein Auftragnehmer mehrere Kostenstruktur-Elemente in einem „Rahmen“ erledigt - zum Beispiel „Lieferung aller Schaltschränke“ - jeder Schaltschrank kann einem anderen Kostenelement zugewiesen werden.
  Da aber keine Abrechnung nach Lieferobjekten erfolgt würden hier nur pauschal die Zahlungsschritte mit beispielsweise 30% bezahlt werden. Die Aufschlüsselung erfolgt über die spätere Bestellposition die genau einem Kostenstruktur-Element (PSP) zugeordnet ist.
  Andersrum kann aber auch nur ein Arbeitspaket auch aus mehreren Vorgängen bestehen um die Arbeitsabläufe auf der Baustelle für mehrere Gewerke zu beschreiben.
  Netzplan/Terminplan:
  Jeder Vertragspartner muss nach der Beauftragung seine Arbeitsabläufe darstellen. Diese müssen aufzeigen wie er das geschuldete Werk (Lieferobjekte) zu den vereinbarten Übergabepunkten bereitstellen will.
  Der H-AN (Hauptauftragnehmer) trägt die Verantwortung die Gesamtheit und Koordinierung ALLER Abläufe und fordert die Zuarbeit der jeweiligen Partner zur Untersetzung des Terminplans ein.
  Der der Terminplan stellt keine Disposition dar, sondern eher Aufgaben und Verantwortungen.
  Phasenplan:
  Gibt an in welche Phasen das Projekt gegliedert werden soll. Es lässt sich daraus die Dauer des Projektes ableiten und grobe kausale Abhängigkeiten abbilden. In der Regel sind diese so detailliert, dass sich die kausalen Bauabschnitte in Form eine Phase wiederfinden. Damit gehen in der Regel Meilensteine einher, die auch für den Mittelfluss der Zahlpläne genutzt werden.

## MS Visio (FMC:Actor)

## Net Construction (DG-LP) (FMC:Actor)

## Net Operation MV/ LV (DG-LI) (FMC:Actor)

## Netzbauauftrag (FMC:State)
- dcterms:description: Kostenübersicht/Deckblatt
- dcterms:type: BPMN:dataObject

## NIP (FMC:Actor)
- dcterms:description:
  - Netzinformationsplattform
  - Fehlerstatistik

## NIS (FMC:Actor)
- dcterms:description: Netz-Informations-System
  - Trimble
  - PlanIT

## NKT XRM (FMC:Actor)
- dcterms:description: Extended-Relationship-Management (XRM)

## NPK Protokoll (FMC:State)
- dcterms:description: Protokoll der Genehmigung aus der Netzplanungskonferenz (NPK).
- dcterms:type: BPMN:dataObject

## NPK Präsentation (FMC:State)
- dcterms:type: BPMN:dataObject

## OPAL (FMC:Actor)
- dcterms:description: Handbuch für die Prozesse in der Mittel/Niederspannung

## Operations & Project Steering HC (DG-VO) (FMC:Actor)

## Operations & Project Steering Metering (DG-MS) (FMC:Actor)

## Operations Management (DG-AO) (FMC:Actor)

## Operations Metering (DG-MB) (FMC:Actor)

## Operations Primary Technology (DG-VP) (FMC:Actor)

## Operations Secondary Technology (DG-VS) (FMC:Actor)

## Organigramm (FMC:State)
- dcterms:description: Rollen:
  - AM
  - PL
  - LA (mehrere Personen, die abhängig von der Projektart/-größe definiert werden... unterschiedliche Hierarchieebenen)
  Kernteam:
  - Bauführer
  - Projektsteuerung (Abteilung Projekt- und Bereichssteuerung)
  - Einkauf
  - TPLs
  - (erweitertes Team wird hier auch schon festgelegt, dieses ist aber noch nicht so stark eingebunden - Spezialisten etc.)
  Beispieldokumente:
  Master-Organigramm.pptx
  Master-Projektorg_E_Teil_UW.pptx
  Links:
  https://vattenfall.sharepoint.com/:p:/r/sites/AnwenderforumBTM/SNAP/Dokumente02/10_Umsetzungsprojekt/TP4-Prozessdetaillierung/03_Ausarbeitungen/Beispieldokumente_Vernetzte_Dokumentation/Master-Organigramm.pptx?d=wbd3785ae53c54e97837b46a6e57f033f&csf=1&e=RfIKeM
  https://vattenfall.sharepoint.com/:p:/r/sites/AnwenderforumBTM/SNAP/Dokumente02/10_Umsetzungsprojekt/TP4-Prozessdetaillierung/03_Ausarbeitungen/Beispieldokumente_Vernetzte_Dokumentation/Master-Projektorg_E_Teil_UW.pptx?d=w0efbf21ecffe4faba2e25602d8474589&csf=1&e=bEZlio
- dcterms:type: BPMN:dataObject

## PlaNet (FMC:Actor)

## Planung (FMC:Actor)

## PlanVest (FMC:Actor)

## PLC (FMC:Actor)
- dcterms:description: Projektleiter-Cockpit

## PowerWork Zähleranschluss-App (FMC:Actor)

## Preis-DB (FMC:State)

## Prognose (FMC:Actor)

## Projektakte (FMC:State)
- dcterms:description: Die "Projektakte" wird basierend auf dem "Projektimpuls" vom Asses Management in der Initialisierungsphase eines Einzelprojektes erstellt. Die Erstellung erfolgt über mehrere Iterationen.
  Enthält:
  - Projektveranlassung
  - Techn. Anschlusskonzept (z.B. DG-AMS-Aktennotiz)
  - Projektkategorie und Projekttyp
  - Typical aus SNAP
  - PV bestimmt
  - technische Lösung (mit Typicals untersetzt)
  - Nebengewerken -> abhängige Projekte
  - Vor-Analyse für die Bestandsnetzabhängigkeit
  - Projekt ist gem. Anforderungen des "Technischen Netzbedarfs" modifiziert
  - Inhalte (was wird in der Maßnahme/dem Projekt gemacht?)
  - Kostenschätzung (gemäß DIN 276)
  - Entscheidung aus NPK 1
  - Planungsrecht berücksichtigt
  - Empfehlung
  - WiRe
  - RBAM
- dcterms:type: BPMN:dataStore

## Projektakte - Dokumentation (FMC:State)
- dcterms:type: BPMN:dataStore

## Projektakte - Dokumentation [Review] (FMC:State)
- dcterms:type: BPMN:dataStore

## Projektakte - Entwurfsplanung (FMC:State)
- dcterms:description: Enthält:
  + alle genehmigungsrelevanten und Betreiber relevanten Unterlagen (hier können je nach Gewerk (Hoch- und Tiefbau, Kabelbau, Anlagenbau) diverse unterschiedliche Dokumente erforderlich sein)
  + Zeichenunterlagen / Planzeichnungen
  + Kostenberechnung (BMG, Zeit, Art) inkl. Mittelfluss je Jahresscheibe planen (DIN 276)
  + Eckterminplan/Phasenplan mit mehr Meilensteinen
  Überarbeitetes Mengengerüst (aus dem Typical) Das Typical wird auf das konkrete Projekt angepasst. Üblicherweise werden die Mengen angepasst.
  + ggf. Genehmigungsplanung (inkl. Baugenehmigung)

## Projektakte - Feinplanung (FMC:State)
- dcterms:description: + ggf. Ausführungsplanung: alle ausführungsrelevanten und Betreiber relevanten Unterlagen (hier können je nach Gewerk (Hoch- und Tiefbau, Kabelbau, Anlagehbau) diverse unterschiedliche Dokumente erforderlich sein
  * Grobplanung: alle genehmigungsrelevanten und Betreiber relevanten Unterlagen (hier können je nach Gewerk (Hoch- und Tiefbau, Kabelbau, Anlagehbau) diverse unterschiedliche Dokumente erforderlich sein)
  * Zeichenunterlagen / Planzeichnungen
  * Kostenberechnung (BMG, Zeit, Art) inkl. Mittelfluss je Jahresscheibe planen (DIN 276)
  * Eckterminplan - Grobplanung (MS Project)
  * ggf. Genehmigungsplanung (inkl. Baugenehmigung)
  * EK-Strategie (Zahlplan)
  + Eckterminplan - Feinplanung (MS Project)
- dcterms:type: BPMN:dataStore

## Projektakte - Feinplanung [Bauführer] (FMC:State)
- dcterms:description: * ggf. Ausführungsplanung: alle ausführungsrelevanten und Betreiber relevanten Unterlagen (hier können je nach Gewerk (Hoch- und Tiefbau, Kabelbau, Anlagenbau) diverse unterschiedliche Dokumente erforderlich sein
  * Grobplanung: alle genehmigungsrelevanten und Betreiber relevanten Unterlagen (hier können je nach Gewerk (Hoch- und Tiefbau, Kabelbau, Anlagenbau) diverse unterschiedliche Dokumente erforderlich sein)
  * Zeichenunterlagen / Planzeichnungen
  * Kostenberechnung (BMG, Zeit, Art) inkl. Mittelfluss je Jahresscheibe planen (DIN 276)
  * Eckterminplan - Ausführungsplanung (MS Project)
  * ggf. Genehmigungsplanung (inkl. Baugenehmigung)

  + Detailterminplan - Ausführungsplanung Bauführer
- dcterms:type: BPMN:dataStore

## Projektakte - Feinplanung [final] (FMC:State)
- dcterms:description: * Ausführungsplanung: alle ausführungsrelevanten und Betreiber relevanten Unterlagen (hier können je nach Gewerk (Hoch- und Tiefbau, Kabelbau, Anlagenbau) diverse unterschiedliche Dokumente erforderlich sein
  * Grobplanung: alle genehmigungsrelevanten und Betreiber relevanten Unterlagen (hier können je nach Gewerk (Hoch- und Tiefbau, Kabelbau, Anlagenbau) diverse unterschiedliche Dokumente erforderlich sein)
  * Zeichenunterlagen / Planzeichnungen
  * Kostenberechnung (BMG, Zeit, Art) inkl. Mittelfluss je Jahresscheibe planen (DIN 276)
  * Detailterminplan - verbindlich (MS Project)
  * ggf. Genehmigungsplanung (inkl. Baugenehmigung)
  * Bestellung

  + Ausführungsplanung (Funktionale Ausschreibung)
  + Detailterminplan - verbindlich (Funktionale Ausschreibung)
- dcterms:type: BPMN:dataStore

## Projektakte - Feinplanung [nach Bestellung] (FMC:State)
- dcterms:description: * ggf. Ausführungsplanung: alle ausführungsrelevanten und Betreiber relevanten Unterlagen (hier können je nach Gewerk (Hoch- und Tiefbau, Kabelbau, Anlagenbau) diverse unterschiedliche Dokumente erforderlich sein
  * Grobplanung: alle genehmigungsrelevanten und Betreiber relevanten Unterlagen (hier können je nach Gewerk (Hoch- und Tiefbau, Kabelbau, Anlagenbau) diverse unterschiedliche Dokumente erforderlich sein)
  * Zeichenunterlagen / Planzeichnungen
  * Kostenberechnung (BMG, Zeit, Art) inkl. Mittelfluss je Jahresscheibe planen (DIN 276)
  * Detailterminplan - tagesscharf (MS Project)
  * ggf. Genehmigungsplanung (inkl. Baugenehmigung)
  + Bestellung
  + Detailterminplan - verbindlich (MS Project)
- dcterms:type: BPMN:dataStore

## Projektakte - PL-Entwurfsplanung (FMC:State)
- dcterms:description: + Umfeldanalyse
  + Stakeholderanalyse
  + Komplikationsliste
  + Risikoliste
  + Prognose
  + Schnittstellen
- dcterms:type: BPMN:dataObject

## Projektakte - Projektstudie (FMC:State)
- dcterms:description: Enthält:
  Inhalt
  - Veranlassung (Grund)
  - Risiko (gemeint ist das Risiko, dass durch die Maßnahme/das Projekt verdrängt wurde)
  - Maßnahmen
  - Planungsrecht
  Zeit
  - Phasenplan (Terminplanung ist präzisiert - Meilensteinplan) (*Typical)
  Struktur
  - PSP-Elementestruktur ist in SAP PM? angelegt (*Typical)
  - Controllingvorgaben (Was muss vom AS in welcher Genauigkeit generell angegeben werden? in SAP...) (Aktuell über PAM Liste definiert. Soll abgelöst werden durch SNAP)
  - Projektstrukturplan
  - Zahlplan pro zukünftiger AN (*Typical)
  Leistung
  - Leistungsverzeichnis mit Mengen und Kosten (AVA) (*Typical)
  Kosten
  - Kostenrahmen (gemäß DIN 276)
  - Kostenschätzung (je LV wird auf MuF und ILV und dann jeweils nach CAPEX OPEX unterschieden)
  - Bestellvorlage (Bündelung der Leistungsverzeichnisse) (*Typical)
  Rollen
  - PL ist benannt (designierter PL)
  - Organigramm nur mit Rollen als Teil des Typicals

## Projektakte - Projektstudie [beauftragt] (FMC:State)
- dcterms:description: Projektstudie (mehrere Dokumente digitale Akte auf dem Server)

  Enthält:

  Inhalt
  * Veranlassung (Grund)
  * Risiko (gemeint ist das Risiko, dass durch die Maßnahme/das Projekt verdrängt wurde)
  * Maßnahmen
  * Planungsrecht

  Zeit
  * Phasenplan (Terminplanung ist präzisiert - Meilensteinplan) (*Typical)

  Struktur
  * PSP-Elementestruktur ist in SAP angelegt (*Typical)
  * Controllingvorgaben (Was muss vom AS in welcher Genauigkeit generell angegeben werden? in SAP...) (Aktuell über PAM Liste definiert. Soll abgelöst werden durch SNAP)
  * Projektstrukturplan
  * Zahlplan pro zukünftiger AN (*Typical)

  Leistung
  * Leistungsverzeichnis mit Mengen und Kosten (AVA) (*Typical)

  Kosten
  * Kostenrahmen (gemäß DIN 276)
  * Kostenschätzung (je LV wird auf MuF und ILV und dann jeweils nach CAPEX OPEX unterschieden)
  * Bestellvorlage (Bündelung der Leistungsverzeichnisse) (*Typical)

  Rollen
  * PL ist benannt (designierter PL)
  * Organigramm nur mit Rollen als Teil des Typicals
- dcterms:type: BPMN:dataObject

## Projektakte - Projektstudie [entworfen] (FMC:State)
- dcterms:description: * Projektveranlassung
  * Techn. Anschlusskonzept (z.B. DG-AMS-Aktennotiz)
  * Projektkategorie und Projekttyp
  * Typical aus SNAP
  * PV bestimmt
  * technische Lösung (mit Typicals untersetzt)
  * Nebengewerken -> abhängige Projekte
  * Vor-Analyse für die Bestandsnetzabhängigkeit
  * "Technischer Netzbedarf" berücksichtigt
  * Inhalte (was wird in der Maßnahme/dem Projekt gemacht?)
  * Kostenschätzung (gemäß DIN 276)
  * Entscheidung aus NPK 1
  * Planungsrecht berücksichtigt
  * WiRe
  * RBAM
  * Empfehlung
  + PL ist benannt
  + Terminplanung ist präzisiert
- dcterms:type: BPMN:dataObject

## Projektakte - Projektstudie [konzipiert] (FMC:State)
- dcterms:description: * Projektveranlassung
  * Techn. Anschlusskonzept (z.B. DG-AMS-Aktennotiz)
  * Projektkategorie und Projekttyp
  * Typical aus SNAP
  * PV bestimmt
  * technische Lösung (mit Typicals untersetzt)
  * Nebengewerken -> abhängige Projekte
  * Vor-Analyse für die Bestandsnetzabhängigkeit
  * "Technischer Netzbedarf" berücksichtigt
  * Inhalte (was wird in der Maßnahme/dem Projekt gemacht?)
  * Kostenschätzung (gemäß DIN 276)
  * Entscheidung aus NPK 1
  * Planungsrecht berücksichtigt
  * Empfehlung
  * WiRe
  * RBAM
  * PL ist benannt
  * Terminplanung ist präzisiert
  * Plausibilitätscheck Asset Service
  + WiRe (überarbeitet)
  + RBAM (überarbeitet)
  + Zuordnung CAPEX/OPEX wenn abweichend zum Projekttypical festgelegt
- dcterms:type: BPMN:dataObject

## Projektakte - Projektstudie [PlausiAS] (FMC:State)
- dcterms:description: * Projektveranlassung
  * Techn. Anschlusskonzept (z.B. DG-AMS-Aktennotiz)
  * Projektkategorie und Projekttyp
  * Typical aus SNAP
  * PV bestimmt
  * technische Lösung (mit Typicals untersetzt)
  * Nebengewerken -> abhängige Projekte
  * Vor-Analyse für die Bestandsnetzabhängigkeit
  * "Technischer Netzbedarf" berücksichtigt
  * Inhalte (was wird in der Maßnahme/dem Projekt gemacht?)
  * Kostenschätzung (gemäß DIN 276)
  * Entscheidung aus NPK 1
  * Planungsrecht berücksichtigt
  * Empfehlung
  * WiRe
  * RBAM
  * PL ist benannt
  * Terminplanung ist präzisiert
  + Plausibilitätscheck Asset Service
- dcterms:type: BPMN:dataObject

## Projektakte - TP-Entwurfsplanung (FMC:State)
- dcterms:description: + Entwurfsplanung: alle genehmigungsrelevanten und Betreiber relevanten Unterlagen (hier können je nach Gewerk (Hoch- und Tiefbau, Kabelbau, Anlagenbau) diverse unterschiedliche Dokumente erforderlich sein)
- dcterms:type: BPMN:dataObject

## Projektakte - TP-Genehmigungsplanung (FMC:State)
- dcterms:description: + Baugenehmigung
  + Genehmigungsunterlagen
- dcterms:type: BPMN:dataObject

## Projektakte - TP-Grobplanung (FMC:State)
- dcterms:description: Verbale Beschreibung dessen was ein AN zu erbringen hat.

  = ausschreibungsreife Leistungsbeschreibung pro Teilprojekt und Vergabeeinheit


  + Anlagen aus der Grobplanung
  + ggf. Genehmigungsplanung (inkl. Baugenehmigung)
- dcterms:type: BPMN:dataObject

## Projektakte [empfohl. Variante_FINAL] (FMC:State)

## Projektakte [Kostenschätzung] (FMC:State)
- dcterms:description: * Projektveranlassung
  * Techn. Anschlusskonzept (z.B. DG-AMS-Aktennotiz)
  * Projektkategorie und Projekttyp
  * Typical aus SNAP
  * PV bestimmt
  * technische Lösung (mit Typicals untersetzt)
  * Nebengewerken -> abhängige Projekte
  * Vor-Analyse für die Bestandsnetzabhängigkeit
  * "Technischer Netzbedarf" berücksichtigt
  * Inhalte (was wird in der Maßnahme/dem Projekt gemacht?)
  * Kostenrahmen (gemäß DIN 276)
  * Entscheidung aus NPK 1
  * Planungsrecht berücksichtigt
  + Kostenschätzung (gemäß DIN 276)
- dcterms:type: BPMN:dataObject

## Projektakte [PlanungsrechtKlar] (FMC:State)
- dcterms:description: * Projektveranlassung
  * Techn. Anschlusskonzept (z.B. DG-AMS-Aktennotiz)
  * Projektkategorie und Projekttyp
  * Typical aus SNAP
  * PV bestimmt
  * technische Lösung
  * Nebengewerken -> abhängige Projekte
  * Vor-Analyse für die Bestandsnetzabhängigkeit
  * "Technischer Netzbedarf" berücksichtigt
  * Inhalte (was wird in der Maßnahme/dem Projekt gemacht?)
  * Kostenrahmen (gemäß DIN 276)
  * Entscheidung aus NPK 1
  + Planungsrecht berücksichtigt
- dcterms:type: BPMN:dataObject

## Projektakte [RBAM/WiRe] (FMC:State)
- dcterms:description: * Projektveranlassung
  * Techn. Anschlusskonzept (z.B. DG-AMS-Aktennotiz)
  * Projektkategorie und Projekttyp
  * Typical aus SNAP
  * PV bestimmt
  * technische Lösung (mit Typicals untersetzt)
  * Nebengewerken -> abhängige Projekte
  * Vor-Analyse für die Bestandsnetzabhängigkeit
  * "Technischer Netzbedarf" berücksichtigt
  * Inhalte (was wird in der Maßnahme/dem Projekt gemacht?)
  * Kostenschätzung (gemäß DIN 276)
  * Entscheidung aus NPK 1
  * Planungsrecht berücksichtigt
  + WiRe
  + RBAM
- dcterms:type: BPMN:dataObject

## Projektakte [techn. Lösung] (FMC:State)
- dcterms:description: * Projektveranlassung
  * Techn. Anschlusskonzept (z.B. DG-AMS-Aktennotiz)
  * Projektkategorie und Projekttyp
  * Typical aus SNAP
  * PV bestimmt

  + technische Lösung
  + Nebengewerken -> abhängige Projekte
  + Vor-Analyse für die Bestandsnetzabhängigkeit
  + "Technischer Netzbedarf" berücksichtigt
- dcterms:type: BPMN:dataObject

## Projektakte [techn. Lösung_Typicals] (FMC:State)
- dcterms:description: * Projektveranlassung
  * Techn. Anschlusskonzept (z.B. DG-AMS-Aktennotiz)
  * Projektkategorie und Projekttyp
  * Typical aus SNAP
  * PV bestimmt
  * technische Lösung
  * Nebengewerken -> abhängige Projekte
  * Vor-Analyse für die Bestandsnetzabhängigkeit
  * "Technischer Netzbedarf" berücksichtigt
  * Inhalte (was wird in der Maßnahme/dem Projekt gemacht?)
  * Kostenrahmen (gemäß DIN 276)
  * Entscheidung aus NPK 1
  * Planungsrecht berücksichtigt
  + technische Lösung (mit Typicals untersetzt)
- dcterms:type: BPMN:dataObject

## Projektakte [Variante_NPK1] (FMC:State)
- dcterms:description: * Projektveranlassung
  * Techn. Anschlusskonzept (z.B. DG-AMS-Aktennotiz)
  * Projektkategorie und Projekttyp
  * Typical aus SNAP
  * PV bestimmt
  * technische Lösung
  * Nebengewerken -> abhängige Projekte
  * Vor-Analyse für die Bestandsnetzabhängigkeit
  * "Technischer Netzbedarf" berücksichtigt
  * Inhalte (was wird in der Maßnahme/dem Projekt gemacht?)
  * Kostenrahmen (gemäß DIN 276)
  + Entscheidung aus NPK1
- dcterms:type: BPMN:dataObject

## Projektakte [Varianten] (FMC:State)
- dcterms:description: Entscheidungsvorlage für die erste Netzplanungkonferenz
  Enthält:
  * Projektveranlassung
  * Techn. Anschlusskonzept (z.B. DG-AMS-Aktennotiz)
  * Projektkategorie und Projekttyp
  * Typical aus SNAP
  * PV bestimmt
  * technische Lösung
  * Nebengewerken -> abhängige Projekte
  * Vor-Analyse für die Bestandsnetzabhängigkeit
  * "Technischer Netzbedarf" berücksichtigt
  + Inhalte (was wird in der Maßnahme/dem Projekt gemacht?)
  + Kostenrahmen (gemäß DIN 276)
- dcterms:type: BPMN:dataObject

## Projektannahme-Empfehlung (FMC:State)
- dcterms:description: Beispieldokument:
  Projektstart-Muster.pdf
  Link:
  https://vattenfall.sharepoint.com/:b:/r/sites/AnwenderforumBTM/SNAP/Dokumente02/10_Umsetzungsprojekt/TP4-Prozessdetaillierung/03_Ausarbeitungen/Beispieldokumente_Vernetzte_Dokumentation/Projektstart-Muster.pdf?csf=1&e=M2nNFt

## Projektannahme-Empfehlung [freigegeben] (FMC:State)
- dcterms:description: Muster 2310 (Projektstart-Muster.pdf)
- dcterms:type: BPMN:dataObject

## Projektannahme-Empfehlung [zur Freigabe] (FMC:State)
- dcterms:description: Muster 2310 (Projektstart-Muster.pdf)
- dcterms:type: BPMN:dataObject

## Projektimpuls (FMC:State)
- dcterms:description:
  - Projektveranlassung
  - Techn. Anschlusskonzept (z.B. DG-AMS-Aktennotiz)
  - Projektkategorie und Projekttyp
  - Typical aus SNAP
  - PV ist bestimmt
- dcterms:type: BPMN:dataObject

## Projektimpuls [Kat+Typ] (FMC:State)
- dcterms:description: * Projektveranlassung
  * Techn. Anschlusskonzept (z.B. DG-AMS-Aktennotiz)
  + Projektkategorie und Projekttyp
  Projektkategorie kann sein:
  - Einzelprojekte (eigenveranlasst)
  - Einzelprojekte (kundenveranlasst)
  - Sammelprojekte (eigenveranlasst)
  - Sammelprojekte (kundenveranlasst)
  - Sammelprojekte (einschl. Anlagenersatz und Umbau)
  + Typical aus SNAP
  + PV bestimmen

  MB: AVA Tools bilden für die LV keine Zeitachse ab. 
  Typicals werden daher letztlich auch Terminpläne enthalten
- dcterms:type: BPMN:dataObject

## Projektmittelantrag (FMC:State)
- dcterms:description: * Beschreibung des Projektzwecks
  * Steht der Projektzweck im ursächlichen Zusammenhang mit einem bereits laufenden Pro-jekt oder mit einem anderen beantragten Projekt oder mit einem zu einem späteren Zeit-punkt beabsichtigten Projekt, ist in dem Projektantrag genau dieser Zusammenhang dar-zulegen; für jedes andere Projekt ist das genehmigte Projektbudget bzw. für beabsichtigte Projekte der voraussichtliche Finanzbedarf anzuzeigen 
  * Terminplan/ Meilensteine, wie z.B. Start, spezifische Etappen des Realisierungsfortschrit-tes, technische Inbetriebnahme, Abschluss
  * Risiken des Projektes
  * Bewertung der Umweltauswirkungen des Projektes
  * Finanzdaten lt. SAP (Ausgaben in das Projekt je Jahresscheibe der geplanten Projekt-laufzeit, für Investitionsprojekte untersetzt nach IFRS-Investitionen für Wachstums- und Ersatzinvestitionen und IFRS-Aufwand in dem Investitionsprojekt, finanzielle Projektreser-ven sind weder zu beantragen noch während der Gesamtlaufzeit zu prognostizieren)
  o	Bei durch Assets veranlassten Projekten sind auch speziell
  	der Finanzanteil „Tec-IT“ (ggf. in der Projektstruktur; generell aber in einem speziellen Textteil des Projektantrages) und für
  	kundenveranlasste Maßnahmen Erlöse/Zuschüsse/Beiträge auszuweisen.
  o	Bei Drittgeschäft-Projekten sind immer auch Erlöse/Zuschüsse/Beiträge auszuwei-sen.
  *WiRe- oder Business Case-Dokumentation (WiRe für Investitions- und Aufwandsprojekte); die Wirtschaftlichkeitsrechnung erfolgt durch Anwendung des entsprechenden, von Ge-schäfts- und Projektcontrolling zur Verfügung gestellten IT-Tools
  o	Speziell für durch Assets veranlassten Projekte
  	WiRe
  	RBAM-Bewertung
  o	Speziell für Drittgeschäft- und IT-Projekte: Business Case
  * Auswirkungen auf die Entwicklung des Personalbestandes durch das Projekt
- dcterms:type: BPMN:dataObject

## Projektsteckbrief PL (FMC:State)
- dcterms:description: Beispieldokument:
  Projektsteckbrief-Muster.PDF
  Link:
  https://vattenfall.sharepoint.com/:b:/r/sites/AnwenderforumBTM/SNAP/Dokumente02/10_Umsetzungsprojekt/TP4-Prozessdetaillierung/03_Ausarbeitungen/Beispieldokumente_Vernetzte_Dokumentation/Projektsteckbrief-Muster.pdf?csf=1&e=2Z3Zv7
- dcterms:type: BPMN:dataObject

## Projektstrukturplan/PAM (FMC:Actor)
- dcterms:description: Planungs- und Angebots-Matrix (PAM)
  Gibt an welche Leistungen ich im Projekt durch wen ausführen lasse. Also ordnet Aufgaben Verantwortlichkeiten zu. Hier drin wird auch definiert welche Leistungen an welche AN vergeben werden sollen. Dabei ist mindestens ein H-AN und n T-AN zu definieren. Es wird auch definiert welche Leistungen in IDL und EGL erfolgen. Dabei werden die ausführenden Bereiche definiert. Darüber können die Kosten der einzelnen Leistungen im Kalkulationsmodell einem AN zugeordnet werden.
  PS: Es gibt derzeit keine saubere Definition wie dieser auszusehen hat. Aber in der Regel wird diese als solcher in verschiedenen Richtungen strukturiert wie beispielsweise in Anlehnung an die Abläufe, die Kostenstruktur, Organigramm oder am Produkt (Lieferobjekte).
  Die Arbeitspakete müssen so klein sein, dass sie genau einem AP Verantwortlichen (kann auch AN sein) und genau einem Kostenstrukturelement zugeordnet, sowie die Übergaben zwischen verschiedenen Vertragspartnern mit ihnen abgebildet werden können
  Ausnahmen bilden übergreifende und Projektbegleitende Leistungen. Hierfür gibt es aber derzeit auch kein übergreifendes PSP-Element. Diese Leistungen sind eher von der Dauer und Komplexität des Projektes getrieben und können bisher nicht sauber abgebildet werden, um diese für zukünftige Kostenschätzung zu verwenden.

## Projektübersichts-Liste (FMC:State)
- dcterms:type: BPMN:dataStore

## ProKoLi (FMC:Actor)
- dcterms:description: Projektkoordinationsliste der HS

## Protokoll Baubesprechung (FMC:State)
- dcterms:type: BPMN:dataObject

## Protokoll Projektmittelantragsprüfung (FMC:State)
- dcterms:type: BPMN:dataObject

## PSP Elemente Planung (FMC:State)
- dcterms:description: Die Planung der PSP Elemente aus einem Typical. Diese wird vom Asset-Management vor der ersten Netzplanungskonferenz (NPK) erstellt und dient später als Grundlage für die PSP Struktur in SAP.
- dcterms:type: BPMN:dataObject

## PUB (FMC:Actor)
- dcterms:description: Prognose Unterstützungsbereiche

## Raumdaten Bau (FMC:State)

## Rechnungs-Erstellung (FMC:Actor)

## Regulatory Management (DG-DR) (FMC:Actor)

## Regulatory Mgmt./ Strategy Dev./MD SNB (DG-D) (FMC:Actor)

## Reporting (FMC:Actor)

## Restpunktliste (FMC:State)
- dcterms:type: BPMN:dataObject

## Roll out (DG-MR) (FMC:Actor)

## Sachdaten-Portal (FMC:Actor)

## SAP (FMC:Actor)
- dcterms:description: Gibt an wie die Kosten aufgeschlüsselt werden müssen. (Aktuell sind dies PSP-Elemente) Das ist wichtig, da diese bei Vertragsgestaltung mit abgebildet werden müssen um eine zu Ordnung der Kosten durch den AN zu ermöglichen.

## SAP (BANF) (FMC:Actor)
- dcterms:description: SAP Bedarfsanforderungen:
  - Leistungsverzeichnisse
  - Auftragsrelevante Unterlagen
  - Ausschreibungsunterlagen
  - Budgetübergabe
  - Bestellpositionen
  - Auftragsnummer
  - Auftragshöhe
  - Lieferdatum
  - Vertragsunterlagen
  (muss übertragbar in Bestellung/Vertrag sein)

## SAP (NeMo) (FMC:Actor)
- dcterms:description: Vattenfall Kostenallokation; implementiert als SNB Modul in SAP-Umgebung.

## SAP Ariba (FMC:Actor)

## SAP PID (FMC:Actor)
- dcterms:description: SAP Workflow - Rechnungsprüfung

## SAP PM (FMC:Actor)

## SAP PS (FMC:Actor)

## SAPCON (FMC:Actor)
- dcterms:description: Generell:
  SAPCON -> erzeugt aus MS Project eine XML-Datei, welche im Anschluss in SAP eingelesen wird und darüber Aufträge und Vorgänge anlegt.
  Auftragsplan:
  Beschreibt ob dem PE(Planungselement/PSP-Element) MuF, EGL und/oder IDL zugeordnet sind.
  - Erzeugung eines Auftrags durch den PL (EGL, MuF oder IGL)
  EGL wird noch mal in 2 Arten unterschieden:
  1) Auftrag Sammler (AS), der definiert auf welchen Kostenstruktur-Elementen die nicht Termin zugeordneten Leistungen der Fachbereiche buchen sollen.
  2) Auftrag Termine (AT), der definiert welche Einsatzorte es unter dem jeweiligen Kostenelement gibt.
  PS: Die beiden Informationen werden für die Applikation APEKS benötigt, über welche/n Einsatz, Erzeugung und Disposition sowie auch die Buchung der kompletten EGL erfolgt.
  Damit wird die Möglichkeit eingeschränkt, dass EGL auf falsche Kostenelemente gebucht werden können.

## SNAP (FMC:Actor)
- dcterms:description: Stromnetz-Analyseplattform mit Funktionsebene und Reportingebene

## SP_KV_MSNS (FMC:State)

## SP_KV_MSNS (FMC:Actor)

## Stakeholder Management & Communication (DG-RM) (FMC:Actor)

## Standardzahlplan (FMC:State)
- dcterms:description: Hierbei handelt es sich um eine Vorlage zur Erstellung des individualisierten Zahlplans.
- dcterms:type: BPMN:dataObject

## Stationsbauauftrag (FMC:State)
- dcterms:type: BPMN:dataObject

## Stationszeichnung (FMC:State)
- dcterms:type: BPMN:dataObject

## Technische Fertigmeldung (FMC:State)

## Technisches Konzept (FMC:State)
- dcterms:description: Das technische Konzept ist das Ergebnis der Planung eines Netzauftrages und enthält
  - Anschlussskizze
  - Bauzaun (NIS)
  - Plan (Netzkonzept, für Kabel, Gebäude und Straßen)
  - koordinierte Netzauftrage
  - Maßnahmenempfehlungen (diese fließen in das Konzept mit ein)
  Bei technischen Konzepten, bei denen eine hohe Wahrscheinlichkeit besteht, dass diese auch tatsächlich beauftragt werden - insbesondere sind die Veranlassungen durch den SKB bis 2MVA - wird noch
  - ein FM Konzept angefragt (da diese Konzepte aufwändig sind werden diese nur für wahrscheinliche Beauftragungen angefragt)
  - Kostenschätzung (DIN 276)
  - Mitnahmen (Fernsteuerung/Automation)

## Technisches Konzept [bemängelt] (FMC:State)
- dcterms:type: BPMN:dataObject

## Technisches Konzept [erstellt] (FMC:State)
- dcterms:description: + Anschlussskizze (Visio, AutoCAD)
  + Bauzaun (NiS)
  + Plan = Netzkonzept (Kabel, Gebäude, Straßen)
  + Netzaufträge koordinieren
  + Maßnahmenempfehlungen einfließen lassen
  + Stationsauftrag erstellen (nur bei Stationen)

  Anmerkung: FM-Konzept & Kostenschätzung (DIN276) wird hier später erstellt als beim Sonderkunden SBK.
- dcterms:type: BPMN:dataObject

## Technisches Konzept [final konzipiert] (FMC:State)
- dcterms:type: BPMN:dataObject

## Technisches Konzept [geprüft] (FMC:State)
- dcterms:type: BPMN:dataObject

## Technisches Konzept [HA final konzipiert] (FMC:State)
- dcterms:description: * Anschlussskizze (Visio, AutoCAD)
  * Bauzaun (NiS)
  * Plan = Netzkonzept (Kabel, Gebäude, Straßen)
  * Netzaufträge koordinieren
  * Maßnahmenempfehlungen einfließen lassen
  * Stationsauftrag erstellen (nur bei Stationen)

  + FM-Konzept
  + Kostenschätzung (DIN 276)
  + Mitnahmen (Fernsteuerung/Automation)
  + Baufreigabe
  + Sanierungsmaßnahmen
- dcterms:type: BPMN:dataObject

## Technisches Konzept [kalkuliert] (FMC:State)
- dcterms:description: Enthält:
  * Anschlussskizze (Visio, AutoCAD)
  * Bauzaun (NiS)
  * Plan = Netzkonzept (Kabel, Gebäude, Straßen)
  * Netzaufträge koordinieren
  * Maßnahmenempfehlungen einfließen lassen
  * FM-Konzept
  * Kostenschätzung (DIN 276)
- dcterms:type: BPMN:dataObject

## Technisches Konzept [SKB final konzipiert] (FMC:State)
- dcterms:description: * Anschlussskizze (Visio, AutoCAD)
  * Bauzaun (NiS)
  * Plan = Netzkonzept (Kabel, Gebäude, Straßen)
  * Netzaufträge koordinieren
  * Maßnahmenempfehlungen einfließen lassen
  * FM-Konzept
  * Kostenschätzung (DIN 276)

  + Mitnahmen (Fernsteuerung/Automation)
  + Baufreigabe
  + Sanierungsmaßnahmen
- dcterms:type: BPMN:dataObject

## Technology Metering (DG-MT) (FMC:Actor)

## Umgebungsdaten (FMC:State)

## Vergabe (FMC:Actor)
- dcterms:description: Modul einer Software zur Ausschreibung, Vergabe und Abrechnung (AVA) von Bauvorhaben.

## Vergabeentscheidung (FMC:State)
- dcterms:type: BPMN:dataObject

## Vertrag Auftragnehmer (AN) (FMC:State)
- dcterms:description: Technischer Teil:
  + Verbindliche Leistungsbeschreibung
  * Anlagen aus der Feinplanung / Grobplanung

  Fachobjekt Vertrag:
  * Leistungsverzeichnis (AVA) / Preisbildungsblatt / Gaeb-Datei (maschinenlesbares LV)
  * Grobterminplan
  * Zahlplan
  + FAQ
  + Verhandlungsprotokoll

  + Bestell-Position inkl. Auftragsnummer

  + kommerzieller Vertragsteil (Bürgschaften,...)
- dcterms:type: BPMN:dataObject

## Vertrag/Verträge mit AN (FMC:State)
- dcterms:type: BPMN:dataObject

## Werksprüfungsprotokoll (FMC:State)
- dcterms:type: BPMN:dataObject

## Zahlplan [Entwurf] (FMC:State)
- dcterms:description: Hierbei handelt es sich um eine Vorlage zur Erstellung des individualisierten Zahlplans.
- dcterms:type: BPMN:dataObject

## Zahlplan [individuell für jede VE] (FMC:State)
- dcterms:type: BPMN:dataObject

## SNB SNAP - Projektprozesse (2020-06-16) (SpecIF:Hierarchy)

## 1:Projekt initialisieren (FMC:Actor)
- dcterms:type: BPMN:callActivity
- dcterms:description: Wird im Subprozess geleistet und in der Projektakte gespeichert: 
  Projektkategorie + Projekttyp
  Erarbeiten der technischen Lösung
  technische Machbarkeit
  Genehmigungsfähigkeit
  Abstimmung mit anderen Projekten (ProKoLi)
  Zeitliche Einteilung in Startjahr + Jahresscheiben
  Mengen und Kostenrahmen nach DIN 276 (= Planungsqualität und Kostenqualität) - aus Typical:
  * Typical = Leistungsverzeichniss(e)? mit Leistungspositionen.
  * Mengen für Leistungspositionen
  * direkte Kosten <-> Projektkosten
  * Kostenstruktur (IST in PlanVeSt, SOLL in SNAP) je Variante 

  Beschreibung (Prosa) der Umsetzungsvarianten
  Projektverantwortlichen (PV) hinterlegen

  -> Kostenrahmen

## 2:Projekt konzipieren (FMC:Actor)
- dcterms:type: BPMN:callActivity

## 3:Projekt beantragen (FMC:Actor)
- dcterms:type: BPMN:callActivity

## 4:Investentscheidung fällen (FMC:Actor)
- dcterms:type: BPMN:userTask

## 6:Projekt realisieren (FMC:Actor)
- dcterms:type: BPMN:callActivity

## 7:Verträge überwachen (FMC:Actor)
- dcterms:type: BPMN:callActivity

## 8:Planungsrunde durchführen (FMC:Actor)
- dcterms:type: BPMN:callActivity

## 9:Projekt reviewen (FMC:Actor)
- dcterms:type: BPMN:task

## Ablage Revision (FMC:State)
- dcterms:type: BPMN:dataStore

## Akteure (SpecIF:Heading)

## Asset Management - Konzeption (FMC:Actor)
- dcterms:type: SpecIF:Role

## Asset Management - Portfoliomanagement (FMC:Actor)
- dcterms:type: SpecIF:Role

## Asset Service (FMC:Actor)
- dcterms:type: SpecIF:Role

## Aufnahme des Projektes in die aktive Planung (FMC:Event)
- dcterms:type: BPMN:startEvent

## boundaryEvent (FMC:Event)
- dcterms:type: BPMN:boundaryEvent

## Einzelprojekt HS (FMC:Actor)
- dcterms:type: BPMN:participant

## endEvent (FMC:Event)
- dcterms:type: BPMN:endEvent

## EP_EV_HS_1_Einzelprojekt-HS (SpecIF:Diagram)
- SpecIF:Diagram: Model View:
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- dcterms:type: SpecIF:BusinessProcess
- dcterms:description: Dieses Prozessdiagramm beschreibt die oberste Ebene eines eigenveranlassten Einzelprojektes in der Hochspannung vom Start bis zum Ende. Dabei repräsentieren die einzelnen Lanes die relevanten Rollen, welche die einzelnen Aufgaben ausführen.

## Ereignisse (SpecIF:Heading)

## Forking Exclusive Gateway: Soll das Projekt beantragt werden? (FMC:Actor)
- dcterms:description: Evaluate the condidition and signal the respective event.
- dcterms:type: BPMN:exclusiveGateway

## Forking Exclusive Gateway: Soll der Invest getätigt werden? (FMC:Actor)
- dcterms:description: Evaluate the condidition and signal the respective event.
- dcterms:type: BPMN:exclusiveGateway

## Geschäftsprozesse (SpecIF:Heading)
- dcterms:type: SpecIF:BusinessProcesses

## Ja (FMC:Event)
- dcterms:type: SpecIF:Condition
- dcterms:description: Forking Exclusive Gateway: Soll das Projekt beantragt werden? → Ja

## Kalkulation (FMC:State)
- dcterms:type: BPMN:dataStore

## Modellelemente (Glossar) (SpecIF:Heading)
- dcterms:type: SpecIF:Glossary

## Nein (FMC:Event)
- dcterms:type: SpecIF:Condition
- dcterms:description: Forking Exclusive Gateway: Soll das Projekt beantragt werden? → Nein

## Nein (FMC:Event)
- dcterms:type: SpecIF:Condition
- dcterms:description: Forking Exclusive Gateway: Soll der Invest getätigt werden? → Nein

## NPK (FMC:Event)
- dcterms:type: BPMN:intermediateCatchEvent
- dcterms:description: Diese Netzplanungskonferenz findet im April statt.

## PA (FMC:Event)
- dcterms:type: BPMN:intermediateThrowEvent
- dcterms:description: Projektakte

## Prognose: PUP, PAM, PLC (FMC:State)
- dcterms:type: BPMN:dataStore
- dcterms:description: + Aktualisierung der zukünftigen Geldflüsse

## Projekt final abgeschlossen (FMC:Event)
- dcterms:type: BPMN:endEvent

## Projektvariante verschieben oder stornieren (FMC:Event)
- dcterms:type: BPMN:endEvent

## Projektvariante zurückgestellt (FMC:Event)
- dcterms:type: BPMN:endEvent

## SNAP (FMC:State)
- dcterms:type: BPMN:dataStore
- dcterms:description: StromNetz Analyse Plattform:
  - Ersetzt z.B. PlanVeSt Kostenstruktur je Umsetzungsvariante und LV
  * CAPEX (Invest)
  * OPEX (Aufwand)
  * Betriebsmittelgruppen
  * EGL, IDL (IVL)

## Terminplan [live] (FMC:State)
- dcterms:type: BPMN:dataObject
- dcterms:description: + Detailterminplan - verbindlich mit Fortschrittsgrad (MS Project)

## Text Annotation 01 (SpecIF:Note)
- dcterms:description: Vorgelagerte Tätigkeiten:
  - DG-AMS & DG-AMC: Ermittlung des Technischen Netzbedarfs aus den Anforderungen für Netzerhalt und Netzausbau (inkl. Gesetzgebung, Betriebliche Anforderungen, Drittveranlasste Maßnahmen, Zustand, Last-/Netzentwicklung, Innovation, etc.)
  - DG-AMC: Bottom up (inkl. Maßnahmen aus Betriebsmittelstrategien)
  - DG-AMP: Technische AO-Anforderungen (QU, Fernsteuerung, Ausfallquoten, etc.)

## Text Annotation 02 (SpecIF:Note)
- dcterms:description: StromNetz Analyse Plattform:
  - Ersetzt z.B. PlanVeSt
  Kostenstruktur je Umsetzungsvariante und LV
  * CAPEX (Invest)
  * OPEX (Aufwand)
  * Betriebsmittelgruppen
  * EGL, IDL (IVL)

## Text Annotation 03 (SpecIF:Note)
- dcterms:description: Diese Netzplanungskonferenz findet im April statt.

## Text Annotation 04 (SpecIF:Note)
- dcterms:description: iv-58

## Text Annotation 05 (SpecIF:Note)
- dcterms:description: NPK    = Netzplanungskonferenz
  IE        = Investment Entscheidung
  TWE   = Technisch-Wirtschaftliche-Entscheidung
  VE       = Vergabe Entscheidung
  PA       = Projekt Abschluss

  Der Projektprozess wird unterschieden in Projektkategorien
  * Einzelprojekte (kunden- oder eigenveranlasst)
  * Sammelprojekte (kunden- oder eigenveranlasst?)
  * Instandhaltungen
  gestartet. In der Initialisierung können als Projektvarianten noch unterschiedliche Projektkategorien entschieden werden. Nach der zweiten NPK wird mit der entschiedenen Projektvariante - und damit auch Projektkategorie - weitergearbeitet

## Text Annotation 06 (SpecIF:Note)
- dcterms:description: UST_Portfoliomgmt_0026
  UST_Portfoliomgmt_0050

## Text Annotation 07 (SpecIF:Note)
- dcterms:description: UST_Portfoliomgmt_0076

## Text Annotation 08 (SpecIF:Note)
- dcterms:description: UST_Portfoliomgmt_0053

## Text Annotation 09 (SpecIF:Note)
- dcterms:description: UST_Portfoliomgmt_0092
  UST_Portfoliomgmt_0024

## Vertrag generiert (FMC:Event)
- dcterms:type: BPMN:boundaryEvent

## Zustände (SpecIF:Heading)

## Geschäftsprozesse (SpecIF:Heading)
- dcterms:type: SpecIF:BusinessProcesses

## Modellelemente (Glossar) (SpecIF:Heading)
- dcterms:type: SpecIF:Glossary

## Akteure (SpecIF:Heading)

## Zustände (SpecIF:Heading)

## Ereignisse (SpecIF:Heading)

## Kollektionen und Gruppen (SpecIF:Heading)

## 10:Projektkategorie und Projekttyp ermitteln (FMC:Actor)
- dcterms:type: BPMN:userTask
- dcterms:description: Für jeden Projekttyp liegt ein Projekttypical vor und kann genutzt werden (Mengen, Zeiten, Kostenrahmen) mit Betriebsmittel, OPEX/CAPEX und Jahresscheiben

## 11:Technische Lösung erarbeiten / überarbeiten (FMC:Actor)
- dcterms:type: BPMN:userTask

## 12:Langfristplanung aktualisieren (FMC:Actor)
- dcterms:type: BPMN:userTask

## 13:Projektvarianten identifizieren (FMC:Actor)
- dcterms:type: BPMN:userTask

## 14:NPK Präsentation vorbereiten (FMC:Actor)
- dcterms:type: BPMN:userTask

## 15:NPK Präsentation einreichen (FMC:Actor)
- dcterms:type: BPMN:sendTask

## 16:Entscheidung aus NPK empfangen (FMC:Actor)
- dcterms:type: BPMN:receiveTask

## 17:Projektsteckbrief mit Protokoll abgleichen (FMC:Actor)
- dcterms:type: BPMN:userTask

## Akteure (SpecIF:Heading)

## EP_EV_HS_1A_Einzelprojekt-HS--Projekt initialisieren (SpecIF:Diagram)
- SpecIF:Diagram: Model View:
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- dcterms:type: SpecIF:BusinessProcess
- dcterms:description: Der Sub-Prozess "Projekt initialisieren" wird durch das Asset Management durchgeführt. Hierbei dient der Projektimpuls als Vorlage für die initiale Erstellung der Projektakte in mehreren Varianten zur Vorlage in der ersten Netzplankonferenz. Als Ergebnis der NPK wird sich im Happy Path auf eine oder mehrere Variante/-n der Projektakte festgelegt. Im Anschluss folgt die nächste Aufgabe - die Konzeption.

## Ereignisse (SpecIF:Heading)

## Forking Exclusive Gateway: Anzahl Varianten >=1? (FMC:Actor)
- dcterms:description: Evaluate the condidition and signal the respective event.
- dcterms:type: BPMN:exclusiveGateway

## Forking Exclusive Gateway: Projekt im Projektprogramm Beginn <3 Jahre? (FMC:Actor)
- dcterms:description: Evaluate the condidition and signal the respective event.
- dcterms:type: BPMN:exclusiveGateway

## Frist (FMC:Event)
- dcterms:type: BPMN:intermediateCatchEvent

## Geschäftsprozesse (SpecIF:Heading)
- dcterms:type: SpecIF:BusinessProcesses

## HS Einzelprojekt - Projekt initialisieren (FMC:Actor)
- dcterms:type: BPMN:participant

## Initialer Projektimpuls erstellt (FMC:Event)
- dcterms:type: BPMN:startEvent

## Ja (FMC:Event)
- dcterms:type: SpecIF:Condition
- dcterms:description: Forking Exclusive Gateway: Projekt im Projektprogramm Beginn <3 Jahre? → Ja

## ja (FMC:Event)
- dcterms:type: SpecIF:Condition
- dcterms:description: Forking Exclusive Gateway: Anzahl 
  Varianten >=1? → ja

## Joining Exclusive Gateway (FMC:Actor)
- dcterms:description: Wait for any one incoming branch to continue.
- dcterms:type: BPMN:exclusiveGateway

## Keine Projektvariante tauglich (FMC:Event)
- dcterms:type: BPMN:endEvent

## Modellelemente (Glossar) (SpecIF:Heading)
- dcterms:type: SpecIF:Glossary

## Nein (FMC:Event)
- dcterms:type: SpecIF:Condition
- dcterms:description: Forking Exclusive Gateway: Projekt im Projektprogramm Beginn <3 Jahre? → Nein

## nein (FMC:Event)
- dcterms:type: SpecIF:Condition
- dcterms:description: Forking Exclusive Gateway: Anzahl 
  Varianten >=1? → nein

## NPK (FMC:Event)
- dcterms:type: BPMN:intermediateCatchEvent
- dcterms:description: Diese Netzplanungskonferenz findet im Oktober statt.

## Projektvarianten bereit zur Konzeption (FMC:Event)
- dcterms:type: BPMN:endEvent

## Text Annotation 01 (SpecIF:Note)
- dcterms:description: * Projektveranlassung
  * Techn. Anschlusskonzept (z.B. DG-AMS-Aktennotiz)
  + Projektkategorie und Projekttyp
  Projektkategorie kann sein:
  - Einzelprojekte (eigenveranlasst)
  - Einzelprojekte (kundenveranlasst)
  - Sammelprojekte (eigenveranlasst)
  - Sammelprojekte (kundenveranlasst)
  - Sammelprojekte (einschl. Anlagenersatz und Umbau)
  + Typical aus SNAP
  + PV bestimmen

  MB: AVA Tools bilden für die LV keine Zeitachse ab. 
  Typicals werden daher letztlich auch Terminpläne enthalten

## Text Annotation 02 (SpecIF:Note)
- dcterms:description: * Projektveranlassung
  * Techn. Anschlusskonzept (z.B. DG-AMS-Aktennotiz)
  * Projektkategorie und Projekttyp
  * Typical aus SNAP
  * PV bestimmt

  + technische Lösung
  + Nebengewerken -> abhängige Projekte
  + Vor-Analyse für die Bestandsnetzabhängigkeit
  + "Technischer Netzbedarf" berücksichtigt

## Text Annotation 03 (SpecIF:Note)
- dcterms:description: Entscheidungsvorlage für die erste Netzplanungskonferenz
  Enthält:
  * Projektveranlassung
  * Techn. Anschlusskonzept (z.B. DG-AMS-Aktennotiz)
  * Projektkategorie und Projekttyp
  * Typical aus SNAP
  * PV bestimmt
  * technische Lösung
  * Nebengewerken -> abhängige Projekte
  * Vor-Analyse für die Bestandsnetzabhängigkeit
  * "Technischer Netzbedarf" berücksichtigt
  + Inhalte (was wird in der Maßnahme/dem Projekt gemacht?)
  + Kostenrahmen (gemäß DIN 276)

## Text Annotation 04 (SpecIF:Note)
- dcterms:description: PowerPoint mit wesentlichen Projektparametern

## Text Annotation 05 (SpecIF:Note)
- dcterms:description: Das "NPK Protokoll" ist kein von SNB benanntes Objekt. Es wurde aus methodischer Sicht hinzugefügt. Wenn es eine Entscheidung in der NPK gibt, dann muss irgendwie der Inhalt der Entscheidung an AM-Konzeption wieder zurückgemeldet werden. Daher wurde hier das Objekt NPK Protokoll eingefügt.
  Annahme: das Protokoll enthält Handlungsanweisungen und Bewertungen der vorgestellten Projektvarianten.

## Text Annotation 06 (SpecIF:Note)
- dcterms:description: * Projektveranlassung
  * Techn. Anschlusskonzept (z.B. DG-AMS-Aktennotiz)
  * Projektkategorie und Projekttyp
  * Typical aus SNAP
  * PV bestimmt
  * technische Lösung
  * Nebengewerken -> abhängige Projekte
  * Vor-Analyse für die Bestandsnetzabhängigkeit
  * "Technischer Netzbedarf" berücksichtigt
  * Inhalte (was wird in der Maßnahme/dem Projekt gemacht?)
  * Kostenrahmen (gemäß DIN 276)
  + Entscheidung aus NPK1

## Text Annotation 07 (SpecIF:Note)
- dcterms:description: + Projektveranlassung
  + Techn. Anschlusskonzept (z.B. DG-AMS-Aktennotiz)

## Text Annotation 08 (SpecIF:Note)
- dcterms:description: + aktualisierte Kalkulation
  + "Technischer Netzbedarf" berücksichtigt

## Text Annotation 09 (SpecIF:Note)
- dcterms:description: UST_AVA/Typicals_0018

## Text Annotation 10 (SpecIF:Note)
- dcterms:description: Typicals

## Text Annotation 11 (SpecIF:Note)
- dcterms:description: Typicals

## Text Annotation 12 (SpecIF:Note)
- dcterms:description: UST_AVA/Typicals_0019

## Text Annotation 13 (SpecIF:Note)
- dcterms:description: Diese Netzplanungskonferenz findet im Oktober statt.

## Text Annotation 14 (SpecIF:Note)
- dcterms:description: UST_Portfoliomgmt_0074b

## Zustände (SpecIF:Heading)

## Geschäftsprozesse (SpecIF:Heading)
- dcterms:type: SpecIF:BusinessProcesses

## Modellelemente (Glossar) (SpecIF:Heading)
- dcterms:type: SpecIF:Glossary

## Akteure (SpecIF:Heading)

## Zustände (SpecIF:Heading)

## Ereignisse (SpecIF:Heading)

## Kollektionen und Gruppen (SpecIF:Heading)

## 18:Projekt je Variante konzipieren (FMC:Actor)
- dcterms:type: BPMN:callActivity

## 19:Projektstudie erstellen (FMC:Actor)
- dcterms:type: BPMN:callActivity
- dcterms:description: Plausibilisierung durch AS
  - inkl. Abgleich interne und externe Ressourcen
  - Beginn im Februar (Dauer 4W für Sichtung der Projektakte + Abschlussbesprechung)

## 20:Typical basierte PSP Struktur erarbeiten (FMC:Actor)
- dcterms:type: BPMN:userTask

## 25:Variante empfehlen und festlegen (FMC:Actor)
- dcterms:type: BPMN:userTask

## Akteure (SpecIF:Heading)

## EP_EV_HS_1B0_Einzelprojekt-HS--Projekt konzipieren (SpecIF:Diagram)
- SpecIF:Diagram: Model View:
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- dcterms:type: SpecIF:BusinessProcess
- dcterms:description: Der Sub-Prozess "Projekt konzipieren" wird durch das Asset Management durchgeführt. Hierbei wird zunächst das Projekt je Variante konzipiert, im Anschluss eine Projektstudie für die empfohlene Variante erstellt und schlussendlich eine Typical basierte PSP Struktur erarbeitet.

## Ereignisse (SpecIF:Heading)

## Geschäftsprozesse (SpecIF:Heading)
- dcterms:type: SpecIF:BusinessProcesses

## HS Einzelprojekt - Projekt konzipieren (FMC:Actor)
- dcterms:type: BPMN:participant

## Konzeption abgeschlossen (FMC:Event)
- dcterms:type: BPMN:endEvent

## Modellelemente (Glossar) (SpecIF:Heading)
- dcterms:type: SpecIF:Glossary

## Projektakte [empfohl. Variante] (FMC:State)
- dcterms:type: BPMN:dataObject
- dcterms:description: * Projektveranlassung
  * Techn. Anschlusskonzept (z.B. DG-AMS-Aktennotiz)
  * Projektkategorie und Projekttyp
  * Typical aus SNAP
  * PV bestimmt
  * technische Lösung (mit Typicals untersetzt)
  * Nebengewerken -> abhängige Projekte
  * Vor-Analyse für die Bestandsnetzabhängigkeit
  * "Technischer Netzbedarf" berücksichtigt
  * Inhalte (was wird in der Maßnahme/dem Projekt gemacht?)
  * Kostenschätzung (gemäß DIN 276)
  * Entscheidung aus NPK 1
  * Planungsrecht berücksichtigt
  * WiRe
  * RBAM
  + Empfehlung

## SAP PS (FMC:State)
- dcterms:type: BPMN:dataStore
- dcterms:description: PS Struktur?

## SNAP (AVA?) (FMC:State)
- dcterms:type: BPMN:dataStore
- dcterms:description: SNAP - für die Typicals

## Text Annotation 01 (SpecIF:Note)
- dcterms:description: MuF über Typicals (mit jahresgenauem Phasenplan)

  EGL+IDL: Personalleistungen müssen nach ihren Aufgaben (Arbeiten) genau zugeordnet werden. (keine prozentuale Zuordnung)

## Text Annotation 02 (SpecIF:Note)
- dcterms:description: Bitte überfprüfen ob hier tatsächlich schon etwas in SAP PS geschrieben wird. Ggf. bitte löschen. 
  Vielleicht: wegen früh anfallender Kosten?

## Text Annotation 03 (SpecIF:Note)
- dcterms:description: Typical wird immer weiter ausdetailliert

## Text Annotation 04 (SpecIF:Note)
- dcterms:description: * Projektveranlassung
  * Techn. Anschlusskonzept (z.B. DG-AMS-Aktennotiz)
  * Projektkategorie und Projekttyp
  * Typical aus SNAP
  * PV bestimmt
  * technische Lösung (mit Typicals untersetzt)
  * Nebengewerken -> abhängige Projekte
  * Vor-Analyse für die Bestandsnetzabhängigkeit
  * "Technischer Netzbedarf" berücksichtigt
  * Inhalte (was wird in der Maßnahme/dem Projekt gemacht?)
  * Kostenschätzung (gemäß DIN 276)
  * Entscheidung aus NPK 1
  * Planungsrecht berücksichtigt
  * WiRe
  * RBAM
  + Empfehlung

## Text Annotation 05 (SpecIF:Note)
- dcterms:description: vorher: AVA

## Text Annotation 06 (SpecIF:Note)
- dcterms:description: Typicals (Kostenmodell)
  PSP-Struktur
  (Betriebsmittelgruppen aufgeilt Budget für Aufwand und Invest)

## Zustände (SpecIF:Heading)

## Geschäftsprozesse (SpecIF:Heading)
- dcterms:type: SpecIF:BusinessProcesses

## Modellelemente (Glossar) (SpecIF:Heading)
- dcterms:type: SpecIF:Glossary

## Akteure (SpecIF:Heading)

## Zustände (SpecIF:Heading)

## Ereignisse (SpecIF:Heading)

## Kollektionen und Gruppen (SpecIF:Heading)

## 21:Planungsrecht klären (FMC:Actor)
- dcterms:type: BPMN:userTask

## 22:Technische Lösung auf Basis von Projekttypicals untersetzen (FMC:Actor)
- dcterms:type: BPMN:userTask

## 23:Kostenschätzung erstellen (FMC:Actor)
- dcterms:type: BPMN:userTask

## 24:WiRe und RBAM berechnen (FMC:Actor)
- dcterms:type: BPMN:userTask

## Akteure (SpecIF:Heading)

## DG-AMP (FMC:Actor)
- dcterms:type: SpecIF:Role

## EP_EV_HS_1B1_Einzelprojekt-HS--Projekt konzipieren--Projekt je Variante konzipieren (SpecIF:Diagram)
- SpecIF:Diagram: Model View:
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- dcterms:type: SpecIF:BusinessProcess
- dcterms:description: Der Sub-Prozess "Projekt je Variante konzipieren" wird durch das Asset Management durchgeführt. Hierbei wird die Projektakte für jede Variante weiter angereichert. Basierend auf der Anreicherung wird eine Variante empfohlen und um eine Wirtschaftlichkeitsrechnung und RBAM ergänzt. Die empfohlene Variante dient im nächsten Sub-Prozess also Basis für die Erstellung der Projektstudie.

## Ereignisse (SpecIF:Heading)

## Geschäftsprozesse (SpecIF:Heading)
- dcterms:type: SpecIF:BusinessProcesses

## HS Einzelprojekt - Projekt konzipieren - Projekt je Variante konzipieren (FMC:Actor)
- dcterms:type: BPMN:participant

## Modellelemente (Glossar) (SpecIF:Heading)
- dcterms:type: SpecIF:Glossary

## Projekt für eine Variante konzipiert (FMC:Event)
- dcterms:type: BPMN:endEvent

## Text Annotation 01 (SpecIF:Note)
- dcterms:description: * Projektveranlassung
  * Techn. Anschlusskonzept (z.B. DG-AMS-Aktennotiz)
  * Projektkategorie und Projekttyp
  * Typical aus SNAP
  * PV bestimmt
  * technische Lösung
  * Nebengewerken -> abhängige Projekte
  * Vor-Analyse für die Bestandsnetzabhängigkeit
  * "Technischer Netzbedarf" berücksichtigt
  * Inhalte (was wird in der Maßnahme/dem Projekt gemacht?)
  * Kostenrahmen (gemäß DIN 276)
  * Entscheidung aus NPK 1
  + Planungsrecht berücksichtigt

## Text Annotation 02 (SpecIF:Note)
- dcterms:description: * Projektveranlassung
  * Techn. Anschlusskonzept (z.B. DG-AMS-Aktennotiz)
  * Projektkategorie und Projekttyp
  * Typical aus SNAP
  * PV bestimmt
  * technische Lösung
  * Nebengewerken -> abhängige Projekte
  * Vor-Analyse für die Bestandsnetzabhängigkeit
  * "Technischer Netzbedarf" berücksichtigt
  * Inhalte (was wird in der Maßnahme/dem Projekt gemacht?)
  * Kostenrahmen (gemäß DIN 276)
  * Entscheidung aus NPK 1
  * Planungsrecht berücksichtigt
  + technische Lösung (mit Typicals untersetzt)

## Text Annotation 03 (SpecIF:Note)
- dcterms:description: * Projektveranlassung
  * Techn. Anschlusskonzept (z.B. DG-AMS-Aktennotiz)
  * Projektkategorie und Projekttyp
  * Typical aus SNAP
  * PV bestimmt
  * technische Lösung (mit Typicals untersetzt)
  * Nebengewerken -> abhängige Projekte
  * Vor-Analyse für die Bestandsnetzabhängigkeit
  * "Technischer Netzbedarf" berücksichtigt
  * Inhalte (was wird in der Maßnahme/dem Projekt gemacht?)
  * Kostenrahmen (gemäß DIN 276)
  * Entscheidung aus NPK 1
  * Planungsrecht berücksichtigt
  + Kostenschätzung (gemäß DIN 276)

## Text Annotation 04 (SpecIF:Note)
- dcterms:description: Typicals

## Text Annotation 05 (SpecIF:Note)
- dcterms:description: * Projektveranlassung
  * Techn. Anschlusskonzept (z.B. DG-AMS-Aktennotiz)
  * Projektkategorie und Projekttyp
  * Typical aus SNAP
  * PV bestimmt
  * technische Lösung (mit Typicals untersetzt)
  * Nebengewerken -> abhängige Projekte
  * Vor-Analyse für die Bestandsnetzabhängigkeit
  * "Technischer Netzbedarf" berücksichtigt
  * Inhalte (was wird in der Maßnahme/dem Projekt gemacht?)
  * Kostenschätzung (gemäß DIN 276)
  * Entscheidung aus NPK 1
  * Planungsrecht berücksichtigt
  + WiRe
  + RBAM

## Text Annotation 06 (SpecIF:Note)
- dcterms:description: UST_Portfoliomgmt_0074a
  UST_Portfoliomgmt_0075
  UST_Portfoliomgmt_NEU2 (wird von Hrn. Osdoba bestimmt)
  UST_Portfoliomgmt_0074

## Zustände (SpecIF:Heading)

## Geschäftsprozesse (SpecIF:Heading)
- dcterms:type: SpecIF:BusinessProcesses

## Modellelemente (Glossar) (SpecIF:Heading)
- dcterms:type: SpecIF:Glossary

## Akteure (SpecIF:Heading)

## Zustände (SpecIF:Heading)

## Ereignisse (SpecIF:Heading)

## Kollektionen und Gruppen (SpecIF:Heading)

## 26:Projektstudie entwerfen / überarbeiten (FMC:Actor)
- dcterms:type: BPMN:userTask
- dcterms:description: Plausibilisierung durch AS
  - inkl. Abgleich interne und externe Ressourcen
  - Beginn im Februar (Dauer 4W für Sichtung der Projektakte + Abschlussbesprechung)

## 27:Projektstudie plausibilisieren (FMC:Actor)
- dcterms:type: BPMN:userTask
- dcterms:description: Plausibilisierung durch AS

  inkl. Abgleich interne und externe Ressourcen

  "Beginn -1a (Feb.)" (Dauer 4W für Sichtung der Akte+Abschlussbesprechung)

## 28:Plausibilisierung prüfen (FMC:Actor)
- dcterms:type: BPMN:task

## 29:Kennzahlen nachberechnen (FMC:Actor)
- dcterms:type: BPMN:userTask

## Akteure (SpecIF:Heading)

## Asset Service - Designiertes Projektteam (FMC:Actor)
- dcterms:type: SpecIF:Role

## EP_EV_HS_1B2_Einzelprojekt-HS--Projekt konzipieren--Projektstudie erstellen (SpecIF:Diagram)
- SpecIF:Diagram: Model View:
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- dcterms:type: SpecIF:BusinessProcess
- dcterms:description: Der Sub-Prozess "Projektstudie erstellen" wird durch das Asset Management in Abstimmung mit dem Asset Service durchgeführt. Die vom Asset Management erstellte Projektstudie wird durch den Asset Service plausibilisiert. Anschließend werden einzelne Kennzahlen nachberechnet und in der Projektstudie ergänzt. Die Projektstudie dient als Basis für die Ergänzung/Erarbeitung der typical basierten PSP Struktur in der nächsten Aufgabe.

## Ereignisse (SpecIF:Heading)

## Forking Exclusive Gateway: Prüfung ok? (FMC:Actor)
- dcterms:description: Evaluate the condidition and signal the respective event.
- dcterms:type: BPMN:exclusiveGateway

## Geschäftsprozesse (SpecIF:Heading)
- dcterms:type: SpecIF:BusinessProcesses

## HS Einzelprojekt - Projekt konzipieren - Projektstudie erstellen (FMC:Actor)
- dcterms:type: BPMN:participant

## Ja (FMC:Event)
- dcterms:type: SpecIF:Condition
- dcterms:description: Forking Exclusive Gateway: Prüfung ok? → Ja

## Joining Exclusive Gateway (FMC:Actor)
- dcterms:description: Wait for any one incoming branch to continue.
- dcterms:type: BPMN:exclusiveGateway

## Modellelemente (Glossar) (SpecIF:Heading)
- dcterms:type: SpecIF:Glossary

## Nein (FMC:Event)
- dcterms:type: SpecIF:Condition
- dcterms:description: Forking Exclusive Gateway: Prüfung ok? → Nein

## Projektstudie konzipiert (FMC:Event)
- dcterms:type: BPMN:endEvent

## Text Annotation 01 (SpecIF:Note)
- dcterms:description: * Projektveranlassung
  * Techn. Anschlusskonzept (z.B. DG-AMS-Aktennotiz)
  * Projektkategorie und Projekttyp
  * Typical aus SNAP
  * PV bestimmt
  * technische Lösung (mit Typicals untersetzt)
  * Nebengewerken -> abhängige Projekte
  * Vor-Analyse für die Bestandsnetzabhängigkeit
  * "Technischer Netzbedarf" berücksichtigt
  * Inhalte (was wird in der Maßnahme/dem Projekt gemacht?)
  * Kostenschätzung (gemäß DIN 276)
  * Entscheidung aus NPK 1
  * Planungsrecht berücksichtigt
  * WiRe
  * RBAM
  * Empfehlung
  + PL ist benannt
  + Terminplanung ist präzisiert

## Text Annotation 02 (SpecIF:Note)
- dcterms:description: * Projektveranlassung
  * Techn. Anschlusskonzept (z.B. DG-AMS-Aktennotiz)
  * Projektkategorie und Projekttyp
  * Typical aus SNAP
  * PV bestimmt
  * technische Lösung (mit Typicals untersetzt)
  * Nebengewerken -> abhängige Projekte
  * Vor-Analyse für die Bestandsnetzabhängigkeit
  * "Technischer Netzbedarf" berücksichtigt
  * Inhalte (was wird in der Maßnahme/dem Projekt gemacht?)
  * Kostenschätzung (gemäß DIN 276)
  * Entscheidung aus NPK 1
  * Planungsrecht berücksichtigt
  * Empfehlung
  * WiRe
  * RBAM
  * PL ist benannt
  * Terminplanung ist präzisiert
  * Plausibilitätscheck Asset Service
  + WiRe (überarbeitet)
  + RBAM (überarbeitet)
  + Zuordnung CAPEX/OPEX wenn abweichend zum Projekttypical festgelegt

## Text Annotation 03 (SpecIF:Note)
- dcterms:description: * Projektveranlassung
  * Techn. Anschlusskonzept (z.B. DG-AMS-Aktennotiz)
  * Projektkategorie und Projekttyp
  * Typical aus SNAP
  * PV bestimmt
  * technische Lösung (mit Typicals untersetzt)
  * Nebengewerken -> abhängige Projekte
  * Vor-Analyse für die Bestandsnetzabhängigkeit
  * "Technischer Netzbedarf" berücksichtigt
  * Inhalte (was wird in der Maßnahme/dem Projekt gemacht?)
  * Kostenschätzung (gemäß DIN 276)
  * Entscheidung aus NPK 1
  * Planungsrecht berücksichtigt
  * Empfehlung
  * WiRe
  * RBAM
  * PL ist benannt
  * Terminplanung ist präzisiert
  + Plausibilitätscheck Asset Service

## Text Annotation 04 (SpecIF:Note)
- dcterms:description: UST_Portfoliomgmt_0077
  UST_Portfoliomgmt_0075
  UST_Portfoliomgmt_NEU2 (wird von Hrn. Osdoba bestimmt)
  UST_Portfoliomgmt_0074

## Zustände (SpecIF:Heading)

## Geschäftsprozesse (SpecIF:Heading)
- dcterms:type: SpecIF:BusinessProcesses

## Modellelemente (Glossar) (SpecIF:Heading)
- dcterms:type: SpecIF:Glossary

## Akteure (SpecIF:Heading)

## Zustände (SpecIF:Heading)

## Ereignisse (SpecIF:Heading)

## Kollektionen und Gruppen (SpecIF:Heading)

## 30:PSP Struktur in SAP einpflegen (FMC:Actor)
- dcterms:type: BPMN:serviceTask

## 31:Projektmittelantrag erstellen (FMC:Actor)
- dcterms:type: BPMN:userTask

## 32:Projektmittelantrag prüfen (FMC:Actor)
- dcterms:type: BPMN:userTask

## 33:Projektstudie nacharbeiten (FMC:Actor)
- dcterms:type: BPMN:userTask

## 34:Projekt an PL übergeben (FMC:Actor)
- dcterms:type: BPMN:userTask

## Akteure (SpecIF:Heading)

## Asset Management (FMC:Actor)
- dcterms:type: SpecIF:Role

## EP_EV_HS_1C_Einzelprojekt-HS--Projekt-beantragen (SpecIF:Diagram)
- SpecIF:Diagram: Model View:
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- dcterms:type: SpecIF:BusinessProcess
- dcterms:description: Der Sub-Prozess "Projekt beantragen" wird durch das Asset Management durchgeführt. Hierbei wird ein Projektmittelantrag erstellt und eine Investmententscheidung herbeigeführt. Bei einer positiven Investmententscheidung wird das Projekt an den Projektleiter im Asset Service übertragen.

## Ereignisse (SpecIF:Heading)

## Forking Exclusive Gateway: Projektmittelantrag bewilligt? (FMC:Actor)
- dcterms:description: Evaluate the condidition and signal the respective event.
- dcterms:type: BPMN:exclusiveGateway

## Geschäftsprozesse (SpecIF:Heading)
- dcterms:type: SpecIF:BusinessProcesses

## Ja (Projekt bewilligt) (FMC:Event)
- dcterms:type: SpecIF:Condition
- dcterms:description: Forking Exclusive Gateway: Projektmittelantrag bewilligt? → Ja (Projekt bewilligt)

## Joining Exclusive Gateway (FMC:Actor)
- dcterms:description: Wait for any one incoming branch to continue.
- dcterms:type: BPMN:exclusiveGateway

## Konzeption abgeschlossen und in NPK bestätigt (FMC:Event)
- dcterms:type: BPMN:startEvent

## Modellelemente (Glossar) (SpecIF:Heading)
- dcterms:type: SpecIF:Glossary

## Nein - Projekt muss nachgearbeitet werden (FMC:Event)
- dcterms:type: SpecIF:Condition
- dcterms:description: Forking Exclusive Gateway: Projektmittelantrag bewilligt? → Nein - Projekt muss nachgearbeitet werden

## Portfolio Management (FMC:Actor)
- dcterms:type: SpecIF:Role

## Projekt ist an PL übergeben (FMC:Event)
- dcterms:type: BPMN:endEvent

## Projektprozess - Projekt beantragen (FMC:Actor)
- dcterms:type: BPMN:participant

## SAP (FMC:State)
- dcterms:type: BPMN:dataStore
- dcterms:description: + Bestellpositionen
  + Auftragsnummer
  + Auftragshöhe
  + Lieferdatum
  + Vertragsunterlagen

## Text Annotation 01 (SpecIF:Note)
- dcterms:description: 5 Kategorien:


  Inhalt
  * Veranlassung (Grund)
  * Risiko (gemeint ist das Risiko, dass durch die Maßnahme/das Projekt verdrängt wurde)
  * Maßnahmen
  * Planungsrecht


  Zeit
  * Phasenplan (Terminplanung ist präzisiert - Meilensteinplan) (*Typical)


  Struktur
  * PSP-Elementestruktur ist in SAP angelegt (*Typical)
  * Controllingvorgaben (Was muss vom AS in welcher Genauigkeit generell angegeben werden? in SAP...) (Aktuell über PAM Liste definiert. Soll abgelöst werden durch SNAP)
  * Projektstrukturplan
  * Zahlplan pro zukünftiger AN (*Typical)


  Leistung
  * Leistungsverzeichnis mit Mengen und Kosten (AVA) (*Typical)


  Kosten
  * Kostenrahmen (gemäß DIN 276)
  * Kostenschätzung (je LV wird auf MuF und ILV und dann jeweils nach CAPEX OPEX unterschieden)
  * Bestellvorlage (Bündelung der Leistungsverzeichnisse) (*Typical)


  Rollen
  * PL ist benannt (designierter PL)
  * Organigramm nur mit Rollen als Teil des Typicals

## Text Annotation 02 (SpecIF:Note)
- dcterms:description: * Beschreibung des Projektzwecks
  * Steht der Projektzweck im ursächlichen Zusammenhang mit einem bereits laufenden Pro-jekt oder mit einem anderen beantragten Projekt oder mit einem zu einem späteren Zeit-punkt beabsichtigten Projekt, ist in dem Projektantrag genau dieser Zusammenhang dar-zulegen; für jedes andere Projekt ist das genehmigte Projektbudget bzw. für beabsichtigte Projekte der voraussichtliche Finanzbedarf anzuzeigen
  * Terminplan/ Meilensteine, wie z.B. Start, spezifische Etappen des Realisierungsfortschrit-tes, technische Inbetriebnahme, Abschluss
  * Risiken des Projektes
  * Bewertung der Umweltauswirkungen des Projektes
  * Finanzdaten lt. SAP (Ausgaben in das Projekt je Jahresscheibe der geplanten Projekt-laufzeit, für Investitionsprojekte untersetzt nach IFRS-Investitionen für Wachstums- und Ersatzinvestitionen und IFRS-Aufwand in dem Investitionsprojekt, finanzielle Projektreser-ven sind weder zu beantragen noch während der Gesamtlaufzeit zu prognostizieren)
  o Bei durch Assets veranlassten Projekten sind auch speziell
  - der Finanzanteil „Tec-IT“ (ggf. in der Projektstruktur; generell aber in einem speziellen Textteil des Projektantrages) und für
  - kundenveranlasste Maßnahmen Erlöse/Zuschüsse/Beiträge auszuweisen.
  o Bei Drittgeschäft-Projekten sind immer auch Erlöse/Zuschüsse/Beiträge auszuwei-sen.
  *WiRe- oder Business Case-Dokumentation (WiRe für Investitions- und Aufwandsprojekte); die Wirtschaftlichkeitsrechnung erfolgt durch Anwendung des entsprechenden, von Ge-schäfts- und Projektcontrolling zur Verfügung gestellten IT-Tools
  o Speziell für durch Assets veranlassten Projekte
  - WiRe
  - RBAM-Bewertung
  o Speziell für Drittgeschäft- und IT-Projekte: Business Case
  * Auswirkungen auf die Entwicklung des Personalbestandes durch das Projekt

## Text Annotation 03 (SpecIF:Note)
- dcterms:description: Klärungsbedarf Hr. Litwiakow

## Text Annotation 04 (SpecIF:Note)
- dcterms:description: oder anderes Format?! - (siehe Projektrichtlinie Seite 8)

## Text Annotation 05 (SpecIF:Note)
- dcterms:description: Ist hier auch schon der Projektsteckbrief erforderlich? (siehe Projektrichtlinie Seite 8)

  Dieses Format ist speziell für das Herbeiführen der Genehmigung durch funktional übergeordnete Organisationseinheiten erforderlich.

## Zustände (SpecIF:Heading)

## Geschäftsprozesse (SpecIF:Heading)
- dcterms:type: SpecIF:BusinessProcesses

## Modellelemente (Glossar) (SpecIF:Heading)
- dcterms:type: SpecIF:Glossary

## Akteure (SpecIF:Heading)

## Zustände (SpecIF:Heading)

## Ereignisse (SpecIF:Heading)

## Kollektionen und Gruppen (SpecIF:Heading)

## 35:Projekt grob planen (FMC:Actor)
- dcterms:type: BPMN:callActivity
- dcterms:description: Ressourcen - Kapazitätsplanung
  (noch nicht Disposition)
  = Bedarfsermittlung aufgeteilt auf Betriebsmittelgruppen und Jahre
  derzeit: Folgejahr monatsscharf, danachfolgende Jahre jahresscharf

## 36:TWE fällen (FMC:Actor)
- dcterms:type: BPMN:task
- dcterms:description: In der TWE ("Technisch Wirtschaftliche Entscheidung") wird der RBAM geprüft, wenn größer 1, dann Gewinn, wenn kleiner Null, dann nur Verlust und kein Projektentscheid.

## 37:Projekt fein planen (FMC:Actor)
- dcterms:type: BPMN:callActivity

## 38:Projekt ausführen (FMC:Actor)
- dcterms:type: BPMN:callActivity

## Akteure (SpecIF:Heading)

## Ausführungsfreigabe (FMC:Event)
- dcterms:type: BPMN:intermediateThrowEvent

## EP_EV_HS_1D0_Einzelprojekt-HS--Projekt realisieren (SpecIF:Diagram)
- SpecIF:Diagram: Model View:
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- dcterms:type: SpecIF:BusinessProcess
- dcterms:description: Der Sub-Prozess "Projekt realisieren" wird durch den Asset Service durchgeführt. Dieser wird in zwei weiteren Sub-Prozesse "Projekt grob planen", "Projekt fein planen" und "Projekt ausführen" aufgeteilt.

## Ereignisse (SpecIF:Heading)

## Forking Exclusive Gateway: TWE positiv? (FMC:Actor)
- dcterms:description: Evaluate the condidition and signal the respective event.
- dcterms:type: BPMN:exclusiveGateway

## Geschäftsprozesse (SpecIF:Heading)
- dcterms:type: SpecIF:BusinessProcesses

## HS Einzelprojekt - Projekt realisieren (FMC:Actor)
- dcterms:type: BPMN:participant

## Modellelemente (Glossar) (SpecIF:Heading)
- dcterms:type: SpecIF:Glossary

## nein (FMC:Event)
- dcterms:type: SpecIF:Condition
- dcterms:description: Forking Exclusive Gateway: TWE positiv? → nein

## Projekt muss neu geplant werden (FMC:Event)
- dcterms:type: BPMN:endEvent

## Projekt technisch fertig gemeldet (FMC:Event)
- dcterms:type: BPMN:endEvent

## Projektakte - Grobplanung (FMC:State)
- dcterms:type: BPMN:dataStore
- dcterms:description: * Grobplanung: alle genehmigungsrelevanten und Betreiber relevanten Unterlagen (hier können je nach Gewerk (Hoch- und Tiefbau, Kabelbau, Anlagenbau) diverse unterschiedliche Dokumente erforderlich sein)
  * Zeichenunterlagen / Planzeichnungen
  * Kostenberechnung (BMG, Zeit, Art) inkl. Mittelfluss je Jahresscheibe planen (DIN 276)
  * Eckterminplan/Phasenplan mit mehr Meilensteinen
  Überarbeitetes Mengengerüst (aus dem Typical) Das Typical wird auf das konkrete Projekt angepasst. Üblicherweise werden die Mengen angepasst.
  * ggf. Genehmigungsplanung (inkl. Baugenehmigung)
  + WiRe (überarbeitet)
  + RBAM (überarbeitet)

## Technische Fertigmeldungen (FMC:State)
- dcterms:type: BPMN:dataObject

## Text Annotation 01 (SpecIF:Note)
- dcterms:description: iv-63

## Verantwortung wurde formal von AM über LA an PL übergeben (FMC:Event)
- dcterms:type: BPMN:startEvent

## Zustände (SpecIF:Heading)

## Geschäftsprozesse (SpecIF:Heading)
- dcterms:type: SpecIF:BusinessProcesses

## Modellelemente (Glossar) (SpecIF:Heading)
- dcterms:type: SpecIF:Glossary

## Akteure (SpecIF:Heading)

## Zustände (SpecIF:Heading)

## Ereignisse (SpecIF:Heading)

## Kollektionen und Gruppen (SpecIF:Heading)

## 39:Auftrag prüfen & ggf. mit AM / LA klären (FMC:Actor)
- dcterms:type: BPMN:userTask
- dcterms:description: Projektauftrag formal & inhaltlich prüfen:
  - Unterlagen prüfen und ggf. fehlende Unterlagen von Projektsteuerung oder AM nachfordern

  Inhaltliche Prüfung:
  - KUSS Analyse
  - Kapazitätsplanung -> Befüllung Projektübersichtsliste
  - TPL lesen die Projektstudie aus und füllen ihre Kapazitätsplanung aus
  - Kapazitätsplanung erfolgt mit dem LA und den jeweiligen Gruppenleitern

## 40:Projekt zur Realisierung freigeben (FMC:Actor)
- dcterms:type: BPMN:userTask
- dcterms:description: Der Lenkungsausschuss prüft die Projektannahmeempfehlung (Qualitätsprüfung) und gibt die Projekt-Grobplanung frei

## 41:PSP Elemente freigeben (FMC:Actor)
- dcterms:type: BPMN:userTask
- dcterms:description: Vorhandene PSP Elemente sind bereits durch Bereichssteuerung angelegt und müssen in diesem Schritt von der Bereichssteuerung freigegeben werden.

  Die PL kann in dem Moment der Freigabe über die finanziellen Mittel verfügen.

## 42:Projekt aufsetzen (FMC:Actor)
- dcterms:type: BPMN:callActivity

## 43:Projekt planen (FMC:Actor)
- dcterms:type: BPMN:callActivity

## 44:WiRe und RBAM überarbeiten (FMC:Actor)
- dcterms:type: BPMN:userTask

## Akteure (SpecIF:Heading)

## Asset Service - Bereichs- und Projektsteuerung (FMC:Actor)
- dcterms:type: SpecIF:Role

## Asset Service - Lenkungsausschuss (FMC:Actor)
- dcterms:type: SpecIF:Role

## Asset Service - Projektleitung (FMC:Actor)
- dcterms:type: SpecIF:Role

## DMS (FMC:State)
- dcterms:type: BPMN:dataStore
- dcterms:description: Dokumentenablage:

  zukünftig in SNAP durch Projektakte / DMS

## EP_EV_HS_1D1_Einzelprojekt-HS--Projekt realisieren--Projekt grob planen (SpecIF:Diagram)
- SpecIF:Diagram: Model View:
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- dcterms:type: SpecIF:BusinessProcess
- dcterms:description: Der Sub-Prozess "Projekt grob planen" wird durch den Asset Service und beigestellten Informationen des Asset Managements durchgeführt. Basierend auf der Projektstudie erfolgt die initiale Prüfung durch den Asset Service und anschließende Freigabe durch einen Lenkungsausschuss. Bei positiver Freigabe gibt die Bereichs- und Projektsteuerung die bereits angelegten PSP Elemente in SAP frei. Im Anschluss kann die Projektleitung das Projekt initial aufsetzen. Nachdem das Projekt aufgesetzt wurde wird die Grobplanung durchgeführt, kaufmännische Kennzahlen überarbeitet und ein finaler Stand in der Projektakte/Grobplanung erstellt.

## Ereignisse (SpecIF:Heading)

## Forking Exclusive Gateway: Grobplanung freigegeben? (FMC:Actor)
- dcterms:description: Evaluate the condidition and signal the respective event.
- dcterms:type: BPMN:exclusiveGateway

## Geschäftsprozesse (SpecIF:Heading)
- dcterms:type: SpecIF:BusinessProcesses

## Grobplanung abgeschlossen (FMC:Event)
- dcterms:type: BPMN:endEvent

## HS Einzelprojekt -- Projekt realisieren - Projekt grob planen (FMC:Actor)
- dcterms:type: BPMN:participant

## ja (FMC:Event)
- dcterms:type: SpecIF:Condition
- dcterms:description: Forking Exclusive Gateway: Grobplanung freigegeben? → ja

## Joining Exclusive Gateway (FMC:Actor)
- dcterms:description: Wait for any one incoming branch to continue.
- dcterms:type: BPMN:exclusiveGateway

## Modellelemente (Glossar) (SpecIF:Heading)
- dcterms:type: SpecIF:Glossary

## Nein (FMC:Event)
- dcterms:type: SpecIF:Condition
- dcterms:description: Forking Exclusive Gateway: Grobplanung freigegeben? → Nein

## Projektstrukturplan/PAM (FMC:State)
- dcterms:type: BPMN:dataStore
- dcterms:description: Gibt an welche Leistungen ich im Projekt durch wen ausführen lasse. Also ordnet Aufgaben Verantwortlichkeiten zu. Hier drin wird auch definiert welche Leistungen an welche AN vergeben werden sollen. Dabei ist mindestens ein H-AN und n T-AN zu definieren. Es wird auch definiert welche Leistungen in IDL und EGL erfolgen. Dabei werden die ausführenden Bereiche definiert. Darüber können die Kosten der einzelnen Leistungen im Kalkulationsmodell einem AN zugeordnet werden. 

  PS: Es gibt derzeit keine saubere Definition wie dieser auszusehen hat. Aber in der Regel wird diese als solcher in verschiedenen Richtungen strukturiert wie beispielsweise in Anlehnung an die Abläufe, die Kostenstruktur, Organigramm oder am Produkt (Lieferobjekte). 
   
  Die Arbeitspakete müssen so klein sein, dass sie genau einem AP Verantwortlichen (kann auch AN sein) und genau einem Kostenstrukturelement zugeordnet, sowie die Übergaben zwischen verschiedenen Vertragspartnern mit ihnen abgebildet werden können 

   Ausnahmen bilden übergreifende und Projektbegleitende Leistungen. Hierfür gibt es aber derzeit auch kein übergreifendes PSP-Element. Diese Leistungen sind eher von der Dauer und Komplexität des Projektes getrieben und können bisher nicht sauber abgebildet werden um diese für zukünftige Kostenschätzung zu verwenden.

## SAPCON (FMC:State)
- dcterms:type: BPMN:dataStore
- dcterms:description: Generell:
  SAPCON -> erzeugt aus MS Project eine XML-Datei, welche im Anschluss in SAP eingelesen wird und darüber Aufträge und Vorgänge anlegt.

  Auftragsplan:

  Beschreibt ob dem PE(Planungselement/PSP-Element) MuF, EGL und/oder IDL zugeordnet sind. 

  * Erzeugung eines Auftrags durch den PL (EGL, MuF oder IGL)

  EGL wird noch mal in 2 Arten unterschieden: 

  1) Auftrag Sammler (AS), der definiert auf welchen Kostenstruktur-Elementen die nicht Termin zugeordneten Leistungen der Fachbereiche buchen sollen. 

  2) Auftrag Termine (AT), der definiert welche Einsatzorte es unter dem jeweiligen Kostenelement gibt. 

  PS: Die beiden Informationen werden für die Applikation APEKS benötigt, über welche/n Einsatz, Erzeugung und Disposition sowie auch die Buchung der kompletten EGL erfolgt. 

  Damit wird die Möglichkeit eingeschränkt, dass EGL auf falsche Kostenelemente gebucht werden können.

## Text Annotation 01 (SpecIF:Note)
- dcterms:description: Projektstudie (mehrere Dokumente digitale Akte auf dem Server)

  Enthält:

  Inhalt
  * Veranlassung (Grund)
  * Risiko (gemeint ist das Risiko, dass durch die Maßnahme/das Projekt verdrängt wurde)
  * Maßnahmen
  * Planungsrecht

  Zeit
  * Phasenplan (Terminplanung ist präzisiert - Meilensteinplan) (*Typical)

  Struktur
  * PSP-Elementestruktur ist in SAP angelegt (*Typical)
  * Controllingvorgaben (Was muss vom AS in welcher Genauigkeit generell angegeben werden? in SAP...) (Aktuell über PAM Liste definiert. Soll abgelöst werden durch SNAP)
  * Projektstrukturplan
  * Zahlplan pro zukünftiger AN (*Typical)

  Leistung
  * Leistungsverzeichnis mit Mengen und Kosten (AVA) (*Typical)

  Kosten
  * Kostenrahmen (gemäß DIN 276)
  * Kostenschätzung (je LV wird auf MuF und ILV und dann jeweils nach CAPEX OPEX unterschieden)
  * Bestellvorlage (Bündelung der Leistungsverzeichnisse) (*Typical)

  Rollen
  * PL ist benannt (designierter PL)
  * Organigramm nur mit Rollen als Teil des Typicals

## Text Annotation 02 (SpecIF:Note)
- dcterms:description: Offene Punkte auf Basis der KUSS-Analyse

## Text Annotation 03 (SpecIF:Note)
- dcterms:description: Abgestimmte & konsolidierte Kapazitätsplanung.
  - personenscharf

## Text Annotation 04 (SpecIF:Note)
- dcterms:description: Enthält:
  + Organisation
  + Inhalt
  + Meilensteine gem. aktueller Planung
  + Operative Kosten gem. aktueller Beauftragung
  + Risiken (Termine, Kosten, Qualität)

  Vorlage:
  Muster 2629 (Projektsteckbrief-Muster.pdf)

## Text Annotation 05 (SpecIF:Note)
- dcterms:description: Rollen:
  * AM
  * PL
  * LA (mehrere Personen, die abhängig von der Projektart/-größe definiert werden... unterschiedliche Hierarchieebenen)

  Kernteam:
  * Bauführer
  * Projektsteuerung (Abteilung Projekt- und Bereichssteuerung)
  * Einkauf
  * TPLs
  * (erweitertes Team wird hier auch schon festgelegt, dieses ist aber noch nicht so stark eingebunden - Spezialisten etc.)

  Vorlage: Master-Organigramm.pptx

## Text Annotation 06 (SpecIF:Note)
- dcterms:description: * Grobplanung: alle genehmigungsrelevanten und Betreiber relevanten Unterlagen (hier können je nach Gewerk (Hoch- und Tiefbau, Kabelbau, Anlagenbau) diverse unterschiedliche Dokumente erforderlich sein)
  * Zeichenunterlagen / Planzeichnungen
  * Kostenberechnung (BMG, Zeit, Art) inkl. Mittelfluss je Jahresscheibe planen (DIN 276)
  * Eckterminplan/Phasenplan mit mehr Meilensteinen
  Überarbeitetes Mengengerüst (aus dem Typical) Das Typical wird auf das konkrete Projekt angepasst. Üblicherweise werden die Mengen angepasst.
  * ggf. Genehmigungsplanung (inkl. Baugenehmigung)
  + WiRe (überarbeitet)
  + RBAM (überarbeitet)

## Text Annotation 07 (SpecIF:Note)
- dcterms:description: Muster 2310 (Projektstart-Muster.pdf)

## Text Annotation 08 (SpecIF:Note)
- dcterms:description: Typicals

## Text Annotation 09 (SpecIF:Note)
- dcterms:description: UST_Portfoliomgmt_0075
  UST_Portfoliomgmt_NEU2 (wird von Hrn. Osdoba bestimmt)
  UST_Portfoliomgmt_0074
  UST_Portfoliomgmt_0079

## Zustände (SpecIF:Heading)

## Geschäftsprozesse (SpecIF:Heading)
- dcterms:type: SpecIF:BusinessProcesses

## Modellelemente (Glossar) (SpecIF:Heading)
- dcterms:type: SpecIF:Glossary

## Akteure (SpecIF:Heading)

## Zustände (SpecIF:Heading)

## Ereignisse (SpecIF:Heading)

## Kollektionen und Gruppen (SpecIF:Heading)

## 45:Projektinfrastruktur anlegen (FMC:Actor)
- dcterms:type: BPMN:userTask
- dcterms:description: Ausgangssituation:
  * PSP-Elemente freigegeben aber ohne Aufträge

  ToDo:
  + zu jedem PSP-Element müssen Aufträge für die jeweiligen Aufgaben angelegt werden (siehe unten)
  QS-Liste zur Entwurfsplanung:
  + Projektablagestruktur erstellen
  + Kommunikationsliste
  + Arbeitspaketbeschreibung


  Wie IST:
  Excel Auftragsvorlage (PSP-Elemente aus SAP) wird ausgefüllt und an den Bereichsunterstützer (Projektassistenz) weitergegeben. Dieser importiert (händisch) die Inhalte in MS Project. Hieraus wird über SAPCON (Addon) eine XML-datei generiert welche wiederum nach SAP importiert wird und dort automatisch Aufträge und Vorgänge anlegt. Die Aufträge und Vorgänge werden automatisch zurück nach SAPCON synchronisiert. Hieraus wird ein Bericht generiert (für MuF und IDL). Dieser Bericht wird für Bestellungen (BANF) und Buchungen (Kapazitätsplanung SAP HR) benötigt. Aufträge die EGL enthalten werden nach APEX übertragen, sodass die EGL nicht Termin zugeordneten Aufwände (AS) buchen können.

## 46:Projektstrukturplan anlegen (FMC:Actor)
- dcterms:type: BPMN:userTask

## 47:Beschaffung von externen Dienstleistern (FMC:Actor)
- dcterms:type: BPMN:userTask
- dcterms:description: Dienstleister:
  - Planer
  - Gutachter
  - ausführende Firmen

## Akteure (SpecIF:Heading)

## AVA (FMC:State)
- dcterms:type: BPMN:dataStore
- dcterms:description: Leistungsverzeichnisse / Abrufe

## EP_EV_HS_1D2_Einzelprojekt-HS--Projekt realisieren--Projekt grob planen--Projekt grob planen--Projekt aufsetzen (SpecIF:Diagram)
- SpecIF:Diagram: Model View:
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- dcterms:type: SpecIF:BusinessProcess
- dcterms:description: Der Sub-Prozess "Projekt aufsetzen" wird durch das Asset Management durchgeführt. Basierend auf der beauftragten Projektstudie wird ein Projektstrukturplan erstellt. Sofern externe Planer zur Erstellung der Grobplanung erforderlich sind, werden diese über den Einkauf bestellt.

## Ereignisse (SpecIF:Heading)

## Forking Exclusive Gateway: Sind externe Planer erforderlich? (FMC:Actor)
- dcterms:description: Evaluate the condidition and signal the respective event.
- dcterms:type: BPMN:exclusiveGateway

## Geschäftsprozesse (SpecIF:Heading)
- dcterms:type: SpecIF:BusinessProcesses

## HS Einzelprojekt - Projekt realisieren - Projekt grob planen - Projekt aufsetzen (FMC:Actor)
- dcterms:type: BPMN:participant

## Ja (FMC:Event)
- dcterms:type: SpecIF:Condition
- dcterms:description: Forking Exclusive Gateway: Sind externe Planer erforderlich? → Ja

## Joining Exclusive Gateway (FMC:Actor)
- dcterms:description: Wait for any one incoming branch to continue.
- dcterms:type: BPMN:exclusiveGateway

## Kickoff durchgeführt (FMC:Event)
- dcterms:type: BPMN:intermediateThrowEvent
- dcterms:description: Projektvorstellung mit allen Projektbeteiligten:
  - Kommunikation der Aufgabenverteilung
  - Erstellung Protokoll mit Anpassungen der Aufgaben als Basis der Erstellung des Projektstrukturplans

## Modellelemente (Glossar) (SpecIF:Heading)
- dcterms:type: SpecIF:Glossary

## Nein (FMC:Event)
- dcterms:type: SpecIF:Condition
- dcterms:description: Forking Exclusive Gateway: Sind externe Planer erforderlich? → Nein

## Projekt initial aufgesetzt (FMC:Event)
- dcterms:type: BPMN:endEvent

## PSP Elemente sind freigegeben (FMC:Event)
- dcterms:type: BPMN:startEvent

## SAP (BANF) (FMC:State)
- dcterms:type: BPMN:dataStore
- dcterms:description: + BANF erstellt

  Enthält:
  + Übergabe der Auftragsrelevanten Unterlagen
  + Übergabe der Leistungsverzeichnisse
  + Budgetübergabe
  + BANF muss Übertragbar in Bestellung/Vertrag sein
  (Quelle "2019-11-12_EIN.AVA Einkauf")

## Text Annotation 01 (SpecIF:Note)
- dcterms:description: + BANF erstellt

  Enthält:
  + Übergabe der Auftragsrelevanten Unterlagen
  + Übergabe der Leistungsverzeichnisse
  + Budgetübergabe
  + BANF muss übertragbar in Bestellung/Vertrag sein
  (Quelle "2019-11-12_EIN.AVA Einkauf")

## Text Annotation 02 (SpecIF:Note)
- dcterms:description: Leistungsverzeichnisse / Abrufe

## Text Annotation 03 (SpecIF:Note)
- dcterms:description: Gibt an welche Leistungen ich im Projekt durch wen ausführen lasse. Also ordnet Aufgaben Verantwortlichkeiten zu. Hier drin wird auch definiert welche Leistungen an welche AN vergeben werden sollen. Dabei ist mindestens ein H-AN und n T-AN zu definieren. Es wird auch definiert welche Leistungen in IDL und EGL erfolgen. Dabei werden die ausführenden Bereiche definiert. Darüber können die Kosten der einzelnen Leistungen im Kalkulationsmodell einem AN zugeordnet werden. 


  PS: Es gibt derzeit keine saubere Definition wie dieser auszusehen hat. Aber in der Regel wird diese als solcher in verschiedenen Richtungen strukturiert wie beispielsweise in Anlehnung an die Abläufe, die Kostenstruktur, Organigramm oder am Produkt (Lieferobjekte). 
   
  Die Arbeitspakete müssen so klein sein, dass sie genau einem AP Verantwortlichen (kann auch AN sein) und genau einem Kostenstrukturelement zugeordnet, sowie die Übergaben zwischen verschiedenen Vertragspartnern mit ihnen abgebildet werden können 


   Ausnahmen bilden übergreifende und Projektbegleitende Leistungen. Hierfür gibt es aber derzeit auch kein übergreifendes PSP-Element. Diese Leistungen sind eher von der Dauer und Komplexität des Projektes getrieben und können bisher nicht sauber abgebildet werden um diese für zukünftige Kostenschätzung zu verwenden.

## Text Annotation 04 (SpecIF:Note)
- dcterms:description: Dokumentenablage:

  zukünftig in SNAP durch Projektakte / DMS

## Text Annotation 05 (SpecIF:Note)
- dcterms:description: Generell:
  SAPCON -> erzeugt aus MS Project eine XML-Datei, welche im Anschluss in SAP eingelesen wird und darüber Aufträge und Vorgänge anlegt.

  Auftragsplan:

  Beschreibt ob dem PE(Planungselement/PSP-Element) MuF, EGL und/oder IDL zugeordnet sind. 

  * Erzeugung eines Auftrags durch den PL (EGL, MuF oder IGL)

  EGL wird noch mal in 2 Arten unterschieden: 

  1) Auftrag Sammler (AS), der definiert auf welchen Kostenstruktur-Elementen die nicht Termin zugeordneten Leistungen der Fachbereiche buchen sollen. 

  2) Auftrag Termine (AT), der definiert welche Einsatzorte es unter dem jeweiligen Kostenelement gibt. 

  PS: Die beiden Informationen werden für die Applikation APEKS benötigt, über welche/n Einsatz, Erzeugung und Disposition sowie auch die Buchung der kompletten EGL erfolgt. 

  Damit wird die Möglichkeit eingeschränkt, dass EGL auf falsche Kostenelemente gebucht werden können.

## Text Annotation 06 (SpecIF:Note)
- dcterms:description: Projektvorstellung mit allen Projektbeteiligten:
  - Kommunikation der Aufgabenverteilung
  - Erstellung Protokoll mit Anpassungen der Aufgaben als Basis der Erstellung des Projektstrukturplans

## Text Annotation 07 (SpecIF:Note)
- dcterms:description: + Bestellpositionen
  + Auftragsnummer
  + Auftragshöhe
  + Lieferdatum
  + Vertragsunterlagen

## Text Annotation 08 (SpecIF:Note)
- dcterms:description: UST_AVA/Typicals_0001

## Text Annotation 09 (SpecIF:Note)
- dcterms:description: Typicals

## Zustände (SpecIF:Heading)

## Geschäftsprozesse (SpecIF:Heading)
- dcterms:type: SpecIF:BusinessProcesses

## Modellelemente (Glossar) (SpecIF:Heading)
- dcterms:type: SpecIF:Glossary

## Akteure (SpecIF:Heading)

## Zustände (SpecIF:Heading)

## Ereignisse (SpecIF:Heading)

## Kollektionen und Gruppen (SpecIF:Heading)

## 48:Entwurfsplanung (FMC:Actor)
- dcterms:type: BPMN:task

## 49:Leistungen konkretisieren (FMC:Actor)
- dcterms:type: BPMN:userTask
- dcterms:description: <p>Mengen und Kosten aus den Typicals werden konkretisiert.

  Durch zu Hilfenahme von Fachexperten</p><p>Aus dem AVA werden die Kosten für die Leistungspositionen gepflegt und die Mengen ergänzt. Im AVA Tool sollten jetzt beauftragungsreife Leistungen stehen.</p><p><br></p>

## 50:Entwurfsplanung (FMC:Actor)
- dcterms:type: BPMN:task

## 51:Genehmigungsplanung (FMC:Actor)
- dcterms:type: BPMN:task

## 52:Vergabeeinheiten erstellen (FMC:Actor)
- dcterms:type: BPMN:task
- dcterms:description: Anlage von Bestellcontainern in AVA

## 53:Leistungspositionen den Vergabeeinheiten zuordnen (FMC:Actor)
- dcterms:type: BPMN:task
- dcterms:description: Alle Leistungspositionen müssen VEs zugeordnet sein. (gebündelte Leistungspositionen für die Bestellung)

## 54:Zahlungsbedingung pro Vergabeeinheit definieren (FMC:Actor)
- dcterms:type: BPMN:task
- dcterms:description: Welche Bedingung muss erfüllt sein damit wieviel % Geld (vom Gesamtwert der VE) an den AN fließt? Cashflow

## 55:Voraussichtliche Beschaffungsdauer ermitteln (FMC:Actor)
- dcterms:type: BPMN:userTask
- dcterms:description: Basierend auf dem erforderlichen Beschaffungsprozess wird die voraussichtliche Beschaffungsdauer der Vergabeeinheiten ermittelt. Diese fließt in den Grobterminplan ein.

## 56:TP-Grobplanung erstellen (FMC:Actor)
- dcterms:type: BPMN:userTask

## 57:Grobplanung erstellen (FMC:Actor)
- dcterms:type: BPMN:task

## Akteure (SpecIF:Heading)

## Asset Service - Teilprojektleitung (Hoch- und Tiefbau, Kabelbau, Anlagenbau) (FMC:Actor)
- dcterms:type: SpecIF:Role

## EP_EV_HS_1D3_Einzelprojekt-HS--Projekt realisieren--Projekt grob planen--Projekt grob planen--Projekt planen (SpecIF:Diagram)
- SpecIF:Diagram: Model View:
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- dcterms:type: SpecIF:BusinessProcess
- dcterms:description: Der Sub-Prozess "Projekt planen" wird durch den Asset Service durchgeführt. Hierbei werden initial Entwurfsplanungen erstellt. Im Anschluss muss gegebenenfalls die Genehmigungsplanung erfolgen. Parallel hierzu erstellt die Projektleitung die Einkaufsstrategie. Basierend hierauf wird der Zahl- und Eckterminplan erstellt. Die bis hierhin erfolgte Planung wird gebündelt und mündet in einer Grobplanung.

## Ereignisse (SpecIF:Heading)

## Forking Exclusive Gateway: Genehmigungsplanung erforderlich? (FMC:Actor)
- dcterms:description: Evaluate the condidition and signal the respective event.
- dcterms:type: BPMN:exclusiveGateway

## Forking Parallel Gateway (FMC:Actor)
- dcterms:description: Forward control to all outgoing branches.
- dcterms:type: BPMN:parallelGateway

## Forking Parallel Gateway (FMC:Actor)
- dcterms:description: Forward control to all outgoing branches.
- dcterms:type: BPMN:parallelGateway

## Gesamtkapazitätsplanung - Unternehmen (FMC:State)
- dcterms:type: BPMN:dataStore
- dcterms:description: Abgestimmte & konsolidierte Kapazitätsplanung
  - Auslastung pro Gruppe pro Jahr in Stunden

## Geschäftsprozesse (SpecIF:Heading)
- dcterms:type: SpecIF:BusinessProcesses

## Grobplanung erstellt (FMC:Event)
- dcterms:type: BPMN:endEvent

## HS Einzelprojekt - Projekt realisieren - Projekt grob planen - Projekt planen (FMC:Actor)
- dcterms:type: BPMN:participant

## Ja (FMC:Event)
- dcterms:type: SpecIF:Condition
- dcterms:description: Forking Exclusive Gateway: Genehmigungsplanung erforderlich? → Ja

## Joining Exclusive Gateway (FMC:Actor)
- dcterms:description: Wait for any one incoming branch to continue.
- dcterms:type: BPMN:exclusiveGateway

## Joining Parallel Gateway (FMC:Actor)
- dcterms:description: Wait for all incoming branches to continue.
- dcterms:type: BPMN:parallelGateway

## Joining Parallel Gateway (FMC:Actor)
- dcterms:description: Wait for all incoming branches to continue.
- dcterms:type: BPMN:parallelGateway

## Modellelemente (Glossar) (SpecIF:Heading)
- dcterms:type: SpecIF:Glossary

## Nein (FMC:Event)
- dcterms:type: SpecIF:Condition
- dcterms:description: Forking Exclusive Gateway: Genehmigungsplanung erforderlich? → Nein

## Text Annotation 01 (SpecIF:Note)
- dcterms:description: Mengen und Kosten aus den Typicals werden konkretisiert.

  (Durch zu Hilfenahme von Fachexperten)

  Im AVA-Tool werden die Kosten für die Leistungspositionen gepflegt/ergänzt/geprüft und die Mengen ergänzt.

## Text Annotation 02 (SpecIF:Note)
- dcterms:description: Hierbei handelt es sich um eine Vorlage zur Erstellung des individualisierten Zahlplans.

## Text Annotation 03 (SpecIF:Note)
- dcterms:description: Hierbei handelt es sich um eine Vorlage zur Erstellung des individualisierten Zahlplans.

## Text Annotation 04 (SpecIF:Note)
- dcterms:description: + Grobplanung: alle genehmigungsrelevanten und Betreiber relevanten Unterlagen (hier können je nach Gewerk (Hoch- und Tiefbau, Kabelbau, Anlagenbau) diverse unterschiedliche Dokumente erforderlich sein)
  + Zeichenunterlagen / Planzeichnungen
  + Kostenberechnung (BMG, Zeit, Art) inkl. Mittelfluss je Jahresscheibe planen (DIN 276)
  + Eckterminplan/Phasenplan mit mehr Meilensteinen
  Überarbeitetes Mengengerüst (aus dem Typical) Das Typical wird auf das konkrete Projekt angepasst. Üblicherweise werden die Mengen angepasst.
  + ggf. Genehmigungsplanung (inkl. Baugenehmigung)
  + EK-Strategie (Zahlplan)

## Text Annotation 05 (SpecIF:Note)
- dcterms:description: Abgestimmte & konsolidierte Kapazitätsplanung
  - Auslastung pro Gruppe pro Jahr in Stunden

## Text Annotation 06 (SpecIF:Note)
- dcterms:description: + Baugenehmigung
  + Genehmigungsunterlagen
  + ggf. Auflagen
  + Sondernutzung

## Text Annotation 07 (SpecIF:Note)
- dcterms:description: + Entwurfsplanung: alle genehmigungsrelevanten und Betreiber relevanten Unterlagen (hier können je nach Gewerk (Hoch- und Tiefbau, Kabelbau, Anlagenbau) diverse unterschiedliche Dokumente erforderlich sein)

## Text Annotation 08 (SpecIF:Note)
- dcterms:description: + Bauabschnitte
  + Meilensteine

  Der vom Asset Management erhaltene Phasenplan wird um Bauabschnitte untersetzt und Meilensteine ergänzt.

## Text Annotation 09 (SpecIF:Note)
- dcterms:description: Leistungspositionen inkl. der zugeordneten Preise.

## Text Annotation 10 (SpecIF:Note)
- dcterms:description: UST_AVA/Typicals_0002
  UST_AVA/Typicals_0003

## Text Annotation 11 (SpecIF:Note)
- dcterms:description: Verbale Beschreibung dessen was ein AN zu erbringen hat.

  = ausschreibungsreife Leistungsbeschreibung pro Teilprojekt und Vergabeeinheit

  + Anlagen aus der Grobplanung
  + ggf. Genehmigungsplanung (inkl. Baugenehmigung)

## Text Annotation 12 (SpecIF:Note)
- dcterms:description: Typicals

## Text Annotation 13 (SpecIF:Note)
- dcterms:description: Typicals

## Text Annotation 14 (SpecIF:Note)
- dcterms:description: AVA bedient sich aus Typicals

## Text Annotation 15 (SpecIF:Note)
- dcterms:description: Typicals

## Text Annotation 16 (SpecIF:Note)
- dcterms:description: + Umfeldanalyse
  + Stakeholderanalyse
  + Komplikationsliste
  + Risikoliste
  + Prognose
  + Schnittstellen

## Zustände (SpecIF:Heading)

## Geschäftsprozesse (SpecIF:Heading)
- dcterms:type: SpecIF:BusinessProcesses

## Modellelemente (Glossar) (SpecIF:Heading)
- dcterms:type: SpecIF:Glossary

## Akteure (SpecIF:Heading)

## Zustände (SpecIF:Heading)

## Ereignisse (SpecIF:Heading)

## Kollektionen und Gruppen (SpecIF:Heading)

## 58:Ausführungsplanung erstellen (FMC:Actor)
- dcterms:type: BPMN:userTask

## 59:Vergabe vorbereiten (FMC:Actor)
- dcterms:type: BPMN:userTask
- dcterms:description: + Leistungsverzeichnisse erstellen
  + aktuelle TBs und Richtilinien heraussuchen
  + Terminplan prüfen
  + Loszuweisung (Leistungen den Losen/Vergebeeinheiten zuweisen
  + Aktualisierung der Inhalte der Feinplanung
  = Vergabepaket/Ausschreibungsunterlagen schnüren

## 60:Beschaffung begleiten und bei Vergabe mitwirken (FMC:Actor)
- dcterms:type: BPMN:callActivity

## 61:Leistungsverzeichnisse in Vergabeeinheiten bündeln (FMC:Actor)
- dcterms:type: BPMN:userTask

## 62:Beschaffung begleiten und bei Vergabe mitwirken (FMC:Actor)
- dcterms:type: BPMN:callActivity

## 63:Ausführungsplan für funktionale VEs ergänzen (FMC:Actor)
- dcterms:type: BPMN:userTask
- dcterms:description: VE=Vergabeeinheiten

## Akteure (SpecIF:Heading)

## Alle Ausschreibungsunterlagen (Teilprojekte) der Vergabeeinheit liegen vor (FMC:Event)
- dcterms:type: BPMN:intermediateCatchEvent

## Asset Service - Teilprojektleiter (Hoch- und Tiefbau, Kabelbau, Anlagenbau) (FMC:Actor)
- dcterms:type: SpecIF:Role

## EP_EV_HS_1D4_Einzelprojekt-HS--Projekt realisieren--Projekt fein planen (SpecIF:Diagram)
- SpecIF:Diagram: Model View:
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- dcterms:type: SpecIF:BusinessProcess
- dcterms:description: Der Sub-Prozess "Projekt fein planen" wird durch den Asset Service  durchgeführt. Die Feinplanung erfolgt auf Basis der Grobplanung. In diesem Prozess erfolgt auch die Begleitung und das Mitwirken bei der Vergabe / Beschaffung.

## Ereignisse (SpecIF:Heading)

## Feinplanung abgeschlossen (FMC:Event)
- dcterms:type: BPMN:endEvent

## Forking Exclusive Gateway: Funktionale Ausschreibung vorhanden? (FMC:Actor)
- dcterms:description: Evaluate the condidition and signal the respective event.
- dcterms:type: BPMN:exclusiveGateway

## Forking Exclusive Gateway: Funktionale Ausschreibung? (FMC:Actor)
- dcterms:description: Evaluate the condidition and signal the respective event.
- dcterms:type: BPMN:exclusiveGateway

## Forking Exclusive Gateway: TP-Ausschreibungsunterlage Teil des Hauptauftragnehmers? (FMC:Actor)
- dcterms:description: Evaluate the condidition and signal the respective event.
- dcterms:type: BPMN:exclusiveGateway

## Geschäftsprozesse (SpecIF:Heading)
- dcterms:type: SpecIF:BusinessProcesses

## HS Einzelprojekt - Projekt realisieren - Projekt fein planen (FMC:Actor)
- dcterms:type: BPMN:participant

## Ja (FMC:Event)
- dcterms:type: SpecIF:Condition
- dcterms:description: Forking Exclusive Gateway: Funktionale Ausschreibung? → Ja

## Ja (FMC:Event)
- dcterms:type: SpecIF:Condition
- dcterms:description: Forking Exclusive Gateway: TP-Ausschreibungsunterlage Teil des Hauptauftragnehmers? → Ja

## Ja (FMC:Event)
- dcterms:type: SpecIF:Condition
- dcterms:description: Forking Exclusive Gateway: Funktionale Ausschreibung vorhanden? → Ja

## Joining Exclusive Gateway (FMC:Actor)
- dcterms:description: Wait for any one incoming branch to continue.
- dcterms:type: BPMN:exclusiveGateway

## Joining Exclusive Gateway (FMC:Actor)
- dcterms:description: Wait for any one incoming branch to continue.
- dcterms:type: BPMN:exclusiveGateway

## Joining Exclusive Gateway (FMC:Actor)
- dcterms:description: Wait for any one incoming branch to continue.
- dcterms:type: BPMN:exclusiveGateway

## Modellelemente (Glossar) (SpecIF:Heading)
- dcterms:type: SpecIF:Glossary

## Nein (FMC:Event)
- dcterms:type: SpecIF:Condition
- dcterms:description: Forking Exclusive Gateway: Funktionale Ausschreibung? → Nein

## Nein (FMC:Event)
- dcterms:type: SpecIF:Condition
- dcterms:description: Forking Exclusive Gateway: Funktionale Ausschreibung vorhanden? → Nein

## Nein (FMC:Event)
- dcterms:type: SpecIF:Condition
- dcterms:description: Forking Exclusive Gateway: TP-Ausschreibungsunterlage Teil des Hauptauftragnehmers? → Nein

## startEvent (FMC:Event)
- dcterms:type: BPMN:startEvent

## subProcess_460817227 (FMC:Actor)
- dcterms:type: BPMN:subProcess

## Text Annotation 01 (SpecIF:Note)
- dcterms:description: + ggf. Ausführungsplanung: alle ausführungsrelevanten und Betreiber relevanten Unterlagen (hier können je nach Gewerk (Hoch- und Tiefbau, Kabelbau, Anlagenbau) diverse unterschiedliche Dokumente erforderlich sein
  * Grobplanung: alle genehmigungsrelevanten und Betreiber relevanten Unterlagen (hier können je nach Gewerk (Hoch- und Tiefbau, Kabelbau, Anlagenbau) diverse unterschiedliche Dokumente erforderlich sein)
  * Zeichenunterlagen / Planzeichnungen
  * Kostenberechnung (BMG, Zeit, Art) inkl. Mittelfluss je Jahresscheibe planen (DIN 276)
  * Eckterminplan - Grobplanung (MS Project)
  * ggf. Genehmigungsplanung (inkl. Baugenehmigung)
  * EK-Strategie (Zahlplan)
  + Detailterminplan - tagesscharf (MS Project)

## Text Annotation 02 (SpecIF:Note)
- dcterms:description: Finale verbale Beschreibung dessen was ein AN zu erbringen hat.

  = Leistungsbeschreibung pro Teilprojekt und Vergabeeinheit (FINAL)

  + Anlagen aus der Feinplanung

## Text Annotation 03 (SpecIF:Note)
- dcterms:description: + Leistungsverzeichnisse erstellen
  + aktuelle TBs und Richtilinien heraussuchen
  + Terminplan prüfen
  + Loszuweisung (Leistungen den Losen/Vergebeeinheiten zuweisen
  + Aktualisierung der Inhalte der Feinplanung
  = Vergabepaket/Ausschreibungsunterlagen schnüren

## Text Annotation 04 (SpecIF:Note)
- dcterms:description: * Ausführungsplanung: alle ausführungsrelevanten und Betreiber relevanten Unterlagen (hier können je nach Gewerk (Hoch- und Tiefbau, Kabelbau, Anlagenbau) diverse unterschiedliche Dokumente erforderlich sein
  * Grobplanung: alle genehmigungsrelevanten und Betreiber relevanten Unterlagen (hier können je nach Gewerk (Hoch- und Tiefbau, Kabelbau, Anlagenbau) diverse unterschiedliche Dokumente erforderlich sein)
  * Zeichenunterlagen / Planzeichnungen
  * Kostenberechnung (BMG, Zeit, Art) inkl. Mittelfluss je Jahresscheibe planen (DIN 276)
  * Detailterminplan - verbindlich (MS Project)
  * ggf. Genehmigungsplanung (inkl. Baugenehmigung)
  * Bestellung

  + Ausführungsplanung (Funktionale Ausschreibung)
  + Detailterminplan - verbindlich (Funktionale Ausschreibung)

## Text Annotation 05 (SpecIF:Note)
- dcterms:description: iv-63

## Text Annotation 06 (SpecIF:Note)
- dcterms:description: je Vergabe

## Text Annotation 07 (SpecIF:Note)
- dcterms:description: Verbale Beschreibung des Resultates der zu erbringenden/liefernden Leistung.

## Text Annotation 08 (SpecIF:Note)
- dcterms:description: * ggf. Ausführungsplanung: alle ausführungsrelevanten und Betreiber relevanten Unterlagen (hier können je nach Gewerk (Hoch- und Tiefbau, Kabelbau, Anlagenbau) diverse unterschiedliche Dokumente erforderlich sein
  * Grobplanung: alle genehmigungsrelevanten und Betreiber relevanten Unterlagen (hier können je nach Gewerk (Hoch- und Tiefbau, Kabelbau, Anlagenbau) diverse unterschiedliche Dokumente erforderlich sein)
  * Zeichenunterlagen / Planzeichnungen
  * Kostenberechnung (BMG, Zeit, Art) inkl. Mittelfluss je Jahresscheibe planen (DIN 276)
  * Detailterminplan - tagesscharf (MS Project)
  * ggf. Genehmigungsplanung (inkl. Baugenehmigung)

  + Bestellung
  + Detailterminplan - verbindlich (MS Project)

## Text Annotation 09 (SpecIF:Note)
- dcterms:description: UST_AVA/Typicals_0004

## Text Annotation 10 (SpecIF:Note)
- dcterms:description: UST_AVA/Typicals_0022UST_AVA/Typicals_0023

## Zustände (SpecIF:Heading)

## Geschäftsprozesse (SpecIF:Heading)
- dcterms:type: SpecIF:BusinessProcesses

## Modellelemente (Glossar) (SpecIF:Heading)
- dcterms:type: SpecIF:Glossary

## Akteure (SpecIF:Heading)

## Zustände (SpecIF:Heading)

## Ereignisse (SpecIF:Heading)

## Kollektionen und Gruppen (SpecIF:Heading)

## 64:Werksprüfung durchführen (FMC:Actor)
- dcterms:type: BPMN:task

## 65:Bauüberwachung durchführen (FMC:Actor)
- dcterms:type: BPMN:userTask
- dcterms:description: Enthält:
  - Bauberatung
  - Begehung
  - Terminplankontrolle
  - technische Klärungen
  - Claimmanagment
  - Abstimmung mit Behörden
  - Aufmaßprüfung
  - Rechnungsprüfung
  - Controlling
  - Bauabnahme AN
  - Öffentlich-rechtliche Abnahme
  - Fertigstellungsanzeige
  - Mängelnachverfolgung

## 66:Dokumentation erstellen (FMC:Actor)
- dcterms:type: BPMN:task

## 67:Abnahme der Vergabeeinheiten durchführen (FMC:Actor)
- dcterms:type: BPMN:task

## 68:Endabrechnung und Projektabschluss durchführen (FMC:Actor)
- dcterms:type: BPMN:userTask

## 69:Lessons Learned übertragen (FMC:Actor)
- dcterms:type: BPMN:userTask

## Akteure (SpecIF:Heading)

## Asset Service - Bauführer (FMC:Actor)
- dcterms:type: SpecIF:Role

## Aufmaß Leistungspositionen (FMC:State)
- dcterms:type: BPMN:dataObject
- dcterms:description: Idee: nur was als Aufmaß gefordert ist, kann später auch geprüft und eingehalten werden, was in den "Leistungsbestätigungs-Dokumente" drin steht.

## EP_EV_HS_1D5_Einzelprojekt-HS--Projekt realisieren--Projekt ausführen (SpecIF:Diagram)
- SpecIF:Diagram: Model View:
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- dcterms:type: SpecIF:BusinessProcess
- dcterms:description: Der Sub-Prozess "Projekt grob ausführen" wird durch den Asset Service durchgeführt. Die Ausführung beinhaltet die Erstellung und Überwachung/Aktualisierung einer Ausführungsplanung. Des Weiteren wird in diesem Sub-Prozess die Bau- und Vertragsüberwachung sowie eine vorgelagerte Werksprüfung modelliert. Im Laufe der Projektausführung wird auch die Abnahme der Einzellose durchgeführt sowie eine finale Dokumentation in der Projektakte erstellt. Am Ende des Prozesses erfolgt der Projektabschluss inklusive Endabrechnung gefolgt von der technischen Fertigmeldung aller Teilprojekte in SAP.

## Ereignisse (SpecIF:Heading)

## Feinplanung abgeschlossen und zur Ausführung freigegeben (FMC:Event)
- dcterms:type: BPMN:startEvent

## FFM (FMC:State)
- dcterms:type: BPMN:dataStore
- dcterms:description: Übersicht Rahmenverträge

## Forking Exclusive Gateway: Vorfertigung im Werk (FMC:Actor)
- dcterms:description: Evaluate the condidition and signal the respective event.
- dcterms:type: BPMN:exclusiveGateway

## Forking Parallel Gateway (FMC:Actor)
- dcterms:description: Forward control to all outgoing branches.
- dcterms:type: BPMN:parallelGateway

## Geschäftsprozesse (SpecIF:Heading)
- dcterms:type: SpecIF:BusinessProcesses

## HS Einzelprojekt - Projekt realisieren - Projekt ausführen (FMC:Actor)
- dcterms:type: BPMN:participant

## Inbetriebnahme/Funktionsnachweis durchgeführt (FMC:Event)
- dcterms:type: BPMN:intermediateThrowEvent

## Ja (FMC:Event)
- dcterms:type: SpecIF:Condition
- dcterms:description: Forking Exclusive Gateway: Vorfertigung im Werk → Ja

## Joining Exclusive Gateway (FMC:Actor)
- dcterms:description: Wait for any one incoming branch to continue.
- dcterms:type: BPMN:exclusiveGateway

## Joining Parallel Gateway (FMC:Actor)
- dcterms:description: Wait for all incoming branches to continue.
- dcterms:type: BPMN:parallelGateway

## Modellelemente (Glossar) (SpecIF:Heading)
- dcterms:type: SpecIF:Glossary

## Nein (FMC:Event)
- dcterms:type: SpecIF:Condition
- dcterms:description: Forking Exclusive Gateway: Vorfertigung im Werk → Nein

## Projekt ist technisch fertig gemeldet (FMC:Event)
- dcterms:type: BPMN:endEvent

## SAP PID (FMC:State)
- dcterms:type: BPMN:dataStore

## technische Fertigmeldungen aller TPs in SAP (FMC:Event)
- dcterms:type: BPMN:intermediateThrowEvent

## Text Annotation 01 (SpecIF:Note)
- dcterms:description: * Schaltungsbücher
  * Masterpläne
  * Werk- und Montagepläne
  * Ausführungspläne
  + Kommentare

## Text Annotation 02 (SpecIF:Note)
- dcterms:description: + Schaltungsbücher
  + Masterpläne
  + Werk- und Montagepläne
  + Ausführungspläne

## Text Annotation 03 (SpecIF:Note)
- dcterms:description: + Einbehalte
  + Termine
  + Vertragsdaten
  + Gewährleistungszeiträume
  + etc.

## Text Annotation 04 (SpecIF:Note)
- dcterms:description: Excel mit Informationen zu den Betriebsmitteln von Externen

## Text Annotation 05 (SpecIF:Note)
- dcterms:description: UST_AVA/Typicals_0016
  UST_AVA/Typicals_0017

## Text Annotation 06 (SpecIF:Note)
- dcterms:description: + Abnahmeprotokolle
  + Aufmaße
  + sonstige Dokumente (definiert im Vertrag)

## Text Annotation 07 (SpecIF:Note)
- dcterms:description: UST_AVA/Typicals_0011
  UST_AVA/Typicals_0012
  UST_AVA/Typicals_0013
  UST_AVA/Typicals_0014
  UST_AVA/Typicals_0015

## Text Annotation 08 (SpecIF:Note)
- dcterms:description: * Ausführungsplanung: alle ausführungsrelevanten und Betreiber relevanten Unterlagen (hier können je nach Gewerk (Hoch- und Tiefbau, Kabelbau, Anlagenbau) diverse unterschiedliche Dokumente erforderlich sein
  * Grobplanung: alle genehmigungsrelevanten und Betreiber relevanten Unterlagen (hier können je nach Gewerk (Hoch- und Tiefbau, Kabelbau, Anlagenbau) diverse unterschiedliche Dokumente erforderlich sein)
  * Zeichenunterlagen / Planzeichnungen
  * Kostenberechnung (BMG, Zeit, Art) inkl. Mittelfluss je Jahresscheibe planen (DIN 276)
  * Detailterminplan - verbindlich (MS Project)
  * ggf. Genehmigungsplanung (inkl. Baugenehmigung)
  * Bestellung

  + Detailterminplan - Bauführer

## Text Annotation 09 (SpecIF:Note)
- dcterms:description: Kostenfeststellung

## Zustände (SpecIF:Heading)

## Geschäftsprozesse (SpecIF:Heading)
- dcterms:type: SpecIF:BusinessProcesses

## Modellelemente (Glossar) (SpecIF:Heading)
- dcterms:type: SpecIF:Glossary

## Akteure (SpecIF:Heading)

## Zustände (SpecIF:Heading)

## Ereignisse (SpecIF:Heading)

## Kollektionen und Gruppen (SpecIF:Heading)

## 70:Vergabeeinheit aus Liste auswählen und BANFen erstellen (FMC:Actor)
- dcterms:type: BPMN:task

## 71:Beschaffungsprozess (FMC:Actor)
- dcterms:type: BPMN:callActivity

## 72:Bestellungen durchführen (FMC:Actor)
- dcterms:type: BPMN:task

## Akteure (SpecIF:Heading)

## Anforderer (FMC:Actor)
- dcterms:type: SpecIF:Role

## Ausschreibungsunterlagen liegen vor (FMC:Event)
- dcterms:type: BPMN:startEvent

## BANF freigegeben (FMC:Event)
- dcterms:type: BPMN:intermediateThrowEvent

## Bestellung für VE erfolgt (FMC:Event)
- dcterms:type: BPMN:endEvent

## Einkauf (FMC:Actor)
- dcterms:type: SpecIF:Role

## EP_EV_HS_1D6_Einzelprojekt-HS--Projekt realisieren--Beschaffung (SpecIF:Diagram)
- SpecIF:Diagram: Model View:
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- dcterms:type: SpecIF:BusinessProcess
- dcterms:description: Der Beschaffungsprozess findet innerhalb der Feinplanung statt. Dieser beinhaltet die Vergabeentscheidung(-en).


  Hinweis: Im Gegensatz zum "Wunderlich-Prozess" können mehrere Vergabeentscheidungen gefällt werden.

## Ereignisse (SpecIF:Heading)

## Geschäftsprozesse (SpecIF:Heading)
- dcterms:type: SpecIF:BusinessProcesses

## HS Einzelprojekt - Projekt realisieren - Projekt fein planen - Beschaffung (FMC:Actor)
- dcterms:type: BPMN:participant

## Modellelemente (Glossar) (SpecIF:Heading)
- dcterms:type: SpecIF:Glossary

## Text Annotation 01 (SpecIF:Note)
- dcterms:description: UST_AVA/Typicals_0005

## Text Annotation 02 (SpecIF:Note)
- dcterms:description: UST_AVA/Typicals_0006
  UST_AVA/Typicals_0007
  UST_AVA/Typicals_0008

## Text Annotation 03 (SpecIF:Note)
- dcterms:description: Technischer Teil:
  + Verbindliche Leistungsbeschreibung
  * Anlagen aus der Feinplanung / Grobplanung

  Fachobjekt Vertrag:
  * Leistungsverzeichnis (AVA) / Preisbildungsblatt / Gaeb-Datei (maschinenlesbares LV)
  * Grobterminplan
  * Zahlplan
  + FAQ
  + Verhandlungsprotokoll
  + Bestell-Position inkl. Auftragsnummer
  + kommerzieller Vertragsteil (Bürgschaften,...)

## Text Annotation 04 (SpecIF:Note)
- dcterms:description: + BANF erstellt
  + Ausschreibungsunterlagen

  Beinhaltet:
  - Übergabe der auftragsrelevanten Unterlagen
  - Übergabe der Leistungsverzeichnisse
  - Budgetübergabe
  - BANF muss Übertragbar in Bestellung/Vertrag sein
  (Quelle "2019-11-12_EIN.AVA Einkauf")

## Text Annotation 05 (SpecIF:Note)
- dcterms:description: Entwurf? Wann ist dies kein Entwurf mehr?

## Text Annotation 06 (SpecIF:Note)
- dcterms:description: UST_AVA/Typicals_0009
  UST_AVA/Typicals_0010

## VE (FMC:Event)
- dcterms:type: BPMN:intermediateThrowEvent

## Zustände (SpecIF:Heading)

## Geschäftsprozesse (SpecIF:Heading)
- dcterms:type: SpecIF:BusinessProcesses

## Modellelemente (Glossar) (SpecIF:Heading)
- dcterms:type: SpecIF:Glossary

## Akteure (SpecIF:Heading)

## Zustände (SpecIF:Heading)

## Ereignisse (SpecIF:Heading)

## Kollektionen und Gruppen (SpecIF:Heading)

## 73:Protokoll erstellen (FMC:Actor)
- dcterms:type: BPMN:userTask

## 74:Dokumentation anpassen (FMC:Actor)
- dcterms:type: BPMN:userTask

## 75:Neu generierte ToDos verteilen (FMC:Actor)
- dcterms:type: BPMN:userTask

## Akteure (SpecIF:Heading)

## EP_EV_HS_1D7_Einzelprojekt-HS--Projekt realisieren--Planungsrunde durchführen (SpecIF:Diagram)
- SpecIF:Diagram: Model View:
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- dcterms:type: SpecIF:BusinessProcess

## Ereignisse (SpecIF:Heading)

## Geschäftsprozesse (SpecIF:Heading)
- dcterms:type: SpecIF:BusinessProcesses

## HS Einzelprojekt -- Planungsrunde durchführen (FMC:Actor)
- dcterms:type: BPMN:participant

## Modellelemente (Glossar) (SpecIF:Heading)
- dcterms:type: SpecIF:Glossary

## Planungsrunde abgeschlossen (FMC:Event)
- dcterms:type: BPMN:endEvent

## Planungsrunde steht an (FMC:Event)
- dcterms:type: BPMN:startEvent

## Protokoll Planungsrunde (FMC:State)
- dcterms:type: BPMN:dataObject

## Text Annotation 01 (SpecIF:Note)
- dcterms:description: Rahmen für:
  - Projektstudie
  - Entwurfsplanungs-Akte
  - Grobplanungs-Akte
  - Feinplanungs-Akte
  - etc.

## Zustände (SpecIF:Heading)

## Geschäftsprozesse (SpecIF:Heading)
- dcterms:type: SpecIF:BusinessProcesses

## Modellelemente (Glossar) (SpecIF:Heading)
- dcterms:type: SpecIF:Glossary

## Akteure (SpecIF:Heading)

## Zustände (SpecIF:Heading)

## Ereignisse (SpecIF:Heading)

## Kollektionen und Gruppen (SpecIF:Heading)

## 1:HA durchführen / Netzauftrag konzipieren (FMC:Actor)
- dcterms:type: BPMN:callActivity

## 2:Netzauftrag SKB konzipieren (FMC:Actor)
- dcterms:type: BPMN:callActivity

## 3:Netzauftrag planen (FMC:Actor)
- dcterms:type: BPMN:callActivity

## 4:Stationsbau planen (FMC:Actor)
- dcterms:type: BPMN:task

## 5:Stationsbau ausführen (FMC:Actor)
- dcterms:type: BPMN:task

## 6:Netzauftrag ausführen (FMC:Actor)
- dcterms:type: BPMN:callActivity

## 7:Netzauftrag in Betrieb überführen (FMC:Actor)
- dcterms:type: BPMN:task

## Akteure (SpecIF:Heading)

## Asset Service - Stationsbau (FMC:Actor)
- dcterms:type: SpecIF:Role

## Ereignisse (SpecIF:Heading)

## Forking Exclusive Gateway: Art der Kundenanfrage? (FMC:Actor)
- dcterms:description: Evaluate the condidition and signal the respective event.
- dcterms:type: BPMN:exclusiveGateway

## Forking Exclusive Gateway: Stationsbau erforderlich? (FMC:Actor)
- dcterms:description: Evaluate the condidition and signal the respective event.
- dcterms:type: BPMN:exclusiveGateway

## Forking Parallel Gateway (FMC:Actor)
- dcterms:description: Forward control to all outgoing branches.
- dcterms:type: BPMN:parallelGateway

## Geschäftsprozesse (SpecIF:Heading)
- dcterms:type: SpecIF:BusinessProcesses

## Ja (FMC:Event)
- dcterms:type: SpecIF:Condition
- dcterms:description: Forking Exclusive Gateway: Stationsbau erforderlich? → Ja

## Joining Exclusive Gateway (FMC:Actor)
- dcterms:description: Wait for any one incoming branch to continue.
- dcterms:type: BPMN:exclusiveGateway

## Joining Exclusive Gateway (FMC:Actor)
- dcterms:description: Wait for any one incoming branch to continue.
- dcterms:type: BPMN:exclusiveGateway

## Joining Parallel Gateway (FMC:Actor)
- dcterms:description: Wait for all incoming branches to continue.
- dcterms:type: BPMN:parallelGateway

## Kundenanfrage eingegangen (FMC:Event)
- dcterms:type: BPMN:startEvent

## Kundenanfrage Niederspannung (FMC:Event)
- dcterms:type: SpecIF:Condition
- dcterms:description: Forking Exclusive Gateway: Art der Kundenanfrage? → Kundenanfrage Niederspannung

## Mittelspannung 10kV (>2MVA) (FMC:Event)
- dcterms:type: SpecIF:Condition
- dcterms:description: Forking Exclusive Gateway: Art der Kundenanfrage? → Mittelspannung 10kV (>2MVA)

## Modellelemente (Glossar) (SpecIF:Heading)
- dcterms:type: SpecIF:Glossary

## Nein (FMC:Event)
- dcterms:type: SpecIF:Condition
- dcterms:description: Forking Exclusive Gateway: Stationsbau erforderlich? → Nein

## Projekt in Betrieb überführt (FMC:Event)
- dcterms:type: BPMN:endEvent

## Sammelprojekt-MS/NS--Netzauftrag konzipieren, planen und ausführen (FMC:Actor)
- dcterms:type: BPMN:participant

## SAP (NeMo) (FMC:State)
- dcterms:type: BPMN:dataStore
- dcterms:description: + Netzauftrag für Netzmaßnahme anlegen
  Enthält:
  + Titel
  + Straße
  + Was wird gemacht?
  + Nummer (von NeMo) generiert
  + CS-Aufträge in NeMo
  + Maßnahmen (empfohlene Maßnahmen, kundenbedingte Maßnahmen, FM-Maßnahmen)
  + Auftragsnummer (5-stellig) zurück melden

## SP_KV_MSNS_2_Sammelprojekt-MSNS--Netzauftrag konzipieren, planen und ausführen (SpecIF:Diagram)
- SpecIF:Diagram: Model View:
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- dcterms:type: SpecIF:BusinessProcess
- dcterms:description: Der Sub-Prozess "Netzauftrag konzipieren, planen und ausführen" wird durch den Asset Service durchgeführt. Der Prozess besteht aus dem Stationsbau sowie der Konzeption, Planung und Ausführung eines Netzauftrags. Zum Ende des Prozesses wird der Netzauftrag in Betrieb übernommen.

## Zustände (SpecIF:Heading)

## Geschäftsprozesse (SpecIF:Heading)
- dcterms:type: SpecIF:BusinessProcesses

## Modellelemente (Glossar) (SpecIF:Heading)
- dcterms:type: SpecIF:Glossary

## Akteure (SpecIF:Heading)

## Zustände (SpecIF:Heading)

## Ereignisse (SpecIF:Heading)

## Kollektionen und Gruppen (SpecIF:Heading)

## 10:Technische Prüfung durchführen (FMC:Actor)
- dcterms:type: BPMN:userTask
- dcterms:description: Die Bewertung beinhaltet die Sichtung der Kundendokumente:
  * Leistungsanfrage
  * Geräte
  * Grundpläne
  * Leistungsbilanz (Datenblätter)
  * Lageplan
  * Anschlusspunkt
  * Adresse
  * HA-Skizzen (optional)
  * Kundenpläne

  Als Ergebnis erfolgt die Entscheidung ob eine Netzmaßnahme aus Sicht der Konzeption notwendig ist.

## 11:Netzauftrag anlegen (FMC:Actor)
- dcterms:type: BPMN:userTask
- dcterms:description: Sofern eine Netzmaßnahme erforderlich ist wird hierzu der entsprechende Netzauftrag in SAP NeMo angelegt. In der gleichen Task wird in NIS der Bauzaun eingezeichnet.

## 12:Technisches Konzept erstellen (FMC:Actor)
- dcterms:type: BPMN:userTask
- dcterms:description: Es erfolgt eine Erstellung des technischen Konzepts in Form einer Zeichnung.

## 13:Angebot erstellen (FMC:Actor)
- dcterms:type: BPMN:userTask
- dcterms:description: Es wird basierend auf den in HAM vorliegenden Informationen (Positionen) ein Angebot gelegt.
  Aus HAM:
  - Zeichnung
  - Kosten
  - Vertrag

## 14:Interne Beauftragung der Netzkonzeption (FMC:Actor)
- dcterms:type: BPMN:task
- dcterms:description: Hier wird ein Workflow gestartet welcher an die Konzeption weitergegeben wird und hier die nächste Aufgabe startet.

## 15:Netzauftrag schließen (FMC:Actor)
- dcterms:type: BPMN:task

## 16:Fachbereiche abfragen/mitnehmen (FMC:Actor)
- dcterms:type: BPMN:userTask

## 17:Maßnahmen berücksichtigen und beauftragen (FMC:Actor)
- dcterms:type: BPMN:userTask
- dcterms:description: Maßnahmen aus anderen Projekten.

## 46:Kostenschätzung erstellen (FMC:Actor)
- dcterms:type: BPMN:task

## 8:Kundenanfrage aufnehmen (FMC:Actor)
- dcterms:type: BPMN:userTask
- dcterms:description: Für die eingegangene Kundenanfrage wird eine HAM-Nummer angelegt. In Doxis werden die Dokumente der Kundenanfrage hochgeladen.

## 9:Kundenanfrage bewerten (FMC:Actor)
- dcterms:type: BPMN:userTask
- dcterms:description: Die Bewertung beinhaltet die Sichtung der Kundendokumente:
  * Leistungsanfrage
  * Geräte
  * Grundpläne
  * Leistungsbilanz (Datenblätter)
  * Lageplan
  * Anschlusspunkt
  * Adresse
  * HA-Skizzen (optional)
  * Kundenpläne

  Als Ergebnis erfolgt die Entscheidung ob eine Netzmaßnahme aus Sicht des Anschlussberaters notwendig ist.

## Akteure (SpecIF:Heading)

## Asset Service - Anschlussberater/Sonderanschlussberater (FMC:Actor)
- dcterms:type: SpecIF:Role

## Asset Service - Netzkonzeption (FMC:Actor)
- dcterms:type: SpecIF:Role

## ECM (Doxis) (FMC:State)
- dcterms:type: BPMN:dataStore
- dcterms:description: Enterprise Content Management System - aktuell Doxis

## Ereignisse (SpecIF:Heading)

## Forking Exclusive Gateway: Angebot vom Kunden angenommen? (FMC:Actor)
- dcterms:description: Evaluate the condidition and signal the respective event.
- dcterms:type: BPMN:exclusiveGateway

## Forking Exclusive Gateway: Netzauftrag erforderlich? (FMC:Actor)
- dcterms:description: Evaluate the condidition and signal the respective event.
- dcterms:type: BPMN:exclusiveGateway

## Forking Exclusive Gateway: Netzmaßnahme notwendig? (FMC:Actor)
- dcterms:description: Evaluate the condidition and signal the respective event.
- dcterms:type: BPMN:exclusiveGateway

## Geschäftsprozesse (SpecIF:Heading)
- dcterms:type: SpecIF:BusinessProcesses

## HAM (FMC:State)
- dcterms:type: BPMN:dataStore

## intermediateCatchEvent (FMC:Event)
- dcterms:type: BPMN:intermediateCatchEvent

## Ja (FMC:Event)
- dcterms:type: SpecIF:Condition
- dcterms:description: Forking Exclusive Gateway: Netzmaßnahme notwendig? → Ja

## Ja (FMC:Event)
- dcterms:type: SpecIF:Condition
- dcterms:description: Forking Exclusive Gateway: Netzauftrag erforderlich? → Ja

## Ja (FMC:Event)
- dcterms:type: SpecIF:Condition
- dcterms:description: Forking Exclusive Gateway: Angebot vom Kunden angenommen? → Ja

## Joining Exclusive Gateway (FMC:Actor)
- dcterms:description: Wait for any one incoming branch to continue.
- dcterms:type: BPMN:exclusiveGateway

## Joining Exclusive Gateway (FMC:Actor)
- dcterms:description: Wait for any one incoming branch to continue.
- dcterms:type: BPMN:exclusiveGateway

## Kundenanfrage NS eingegangen (FMC:Event)
- dcterms:type: BPMN:startEvent

## Ledan (FMC:State)
- dcterms:type: BPMN:dataStore

## LiveLink (FMC:State)
- dcterms:type: BPMN:dataStore

## Modellelemente (Glossar) (SpecIF:Heading)
- dcterms:type: SpecIF:Glossary

## MS Excel - Leistungsberechnung (FMC:State)
- dcterms:type: BPMN:dataStore
- dcterms:description: Unterstützungstool

## Nein (FMC:Event)
- dcterms:type: SpecIF:Condition
- dcterms:description: Forking Exclusive Gateway: Netzmaßnahme notwendig? → Nein

## Nein (FMC:Event)
- dcterms:type: SpecIF:Condition
- dcterms:description: Forking Exclusive Gateway: Netzauftrag erforderlich? → Nein

## Nein (FMC:Event)
- dcterms:type: SpecIF:Condition
- dcterms:description: Forking Exclusive Gateway: Angebot vom Kunden angenommen? → Nein

## Netzauftrag geschlossen (FMC:Event)
- dcterms:type: BPMN:endEvent

## Netzauftrag ist konzipiert (FMC:Event)
- dcterms:type: BPMN:endEvent

## NIS (FMC:State)
- dcterms:type: BPMN:dataStore
- dcterms:description: + Bauzaun anlegen

## Sachdatenportal (FMC:State)
- dcterms:type: BPMN:dataStore

## Sammelprojekt -MS/NS--Netzauftrag konzipieren-Netzauftrag für HA-Kunden konzipieren (FMC:Actor)
- dcterms:type: BPMN:participant

## SP_KV_MSNS_2A_Sammelprojekt-MSNS--Netzauftrag konzipieren_HA (SpecIF:Diagram)
- SpecIF:Diagram: Model View:
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- dcterms:type: SpecIF:BusinessProcess
- dcterms:description: Der Sub-Prozess "Netzauftrag für HA-Kunden konzipieren" wird durch den Asset Service durchgeführt. Eingehende Kundenanfragen in der Niederspannung werden durch den Anschlussberater oder Sonderanschlussberater aufgenommen und bewertet. Sofern keine Netzmaßnahme notwendig ist, wird dem Kunden ein Angebot für den Netzanschluss unterbreitet. Falls eine Netzmaßnahme notwendig ist, prüft die Netzkonzeption ob diese auch aus technischer Sicht erforderlich ist. Falls ja, wird ein Netzauftrag in SAP (NeMo) angelegt und ein technisches Konzept erstellt bevor das Angebot erstellt werden kann. Zum Ende der Konzeption werden die anderen Fachbereiche zwecks Mitnahmen und gegebenenfalls tangierenden Projekten abgefragt. Die Ergebnisse fließen in das final konzipierte technische Konzept ein.

## Text Annotation 01 (SpecIF:Note)
- dcterms:description: + Netzauftrag für Netzmaßnahme anlegen
  Enthält:
  + Titel
  + Straße
  + Was wird gemacht?
  + Nummer (von NeMo) generiert
  + CS-Aufträge in NeMo
  + Maßnahmen (empfohlene Maßnahmen, kundenbedingte Maßnahmen, FM-Maßnahmen)
  + Auftragsnummer (5-stellig) zurück melden

## Text Annotation 02 (SpecIF:Note)
- dcterms:description: + Anschlussskizze (Visio, AutoCAD)
  + Bauzaun (NiS)
  + Plan = Netzkonzept (Kabel, Gebäude, Straßen)
  + Netzaufträge koordiniert 
  + Maßnahmenempfehlungen einfließen lassen
  + Stationsauftrag erstellen (nur bei Stationen)

## Text Annotation 03 (SpecIF:Note)
- dcterms:description: * Anschlussskizze (Visio, AutoCAD)
  * Bauzaun (NiS)
  * Plan = Netzkonzept (Kabel, Gebäude, Straßen)
  * Netzaufträge koordiniert
  * Maßnahmenempfehlungen einfließen lassen
  * Stationsauftrag erstellen (nur bei Stationen)

  + FM/LWL-Konzept
  + Mitnahmen (Fernsteuerung/Automation)
  + Baufreigabe
  + Sanierungsmaßnahmen
  + aktualisierte Kostenschätzung (DIN 276)

## Text Annotation 04 (SpecIF:Note)
- dcterms:description: + Bauzaun anlegen

## Text Annotation 05 (SpecIF:Note)
- dcterms:description: Überschneidungen / Abgrenzung von AVA und Typicals sind noch einmal im Detail zu beleuchten.
  Sind Typicals bereits in AVA enthalten bzw. werden sie dort in Zukunft gepflegt?

## Text Annotation 06 (SpecIF:Note)
- dcterms:description: * Leistungsanfrage
  * Geräte
  * Grundpläne
  * Leistungsbilanz (Datenblätter)
  * Lageplan
  * Anschlusspunkt
  * Adresse
  * HA-Skizzen (optional)
  * Kundenpläne

## Text Annotation 07 (SpecIF:Note)
- dcterms:description: * Leistungsanfrage
  * Geräte
  * Grundpläne
  * Leistungsbilanz (Datenblätter)
  * Lageplan
  * Anschlusspunkt
  * Adresse
  * HA-Skizzen (optional)
  * Kundenpläne
  + Bewertung

## Text Annotation 08 (SpecIF:Note)
- dcterms:description: Enterprise Content Management System - aktuell Doxis

## Text Annotation 09 (SpecIF:Note)
- dcterms:description: Kann das vorhandene Netz ohne Veränderung die benötigte Leistung bereitstellen?

## Text Annotation 10 (SpecIF:Note)
- dcterms:description: Budget und Erwartungen, wie dieses eingesetzt wird.

## Text Annotation 11 (SpecIF:Note)
- dcterms:description: UST_AVA/Typicals_0001

## Text Annotation 12 (SpecIF:Note)
- dcterms:description: UST_AVA/Typicals_0002
  UST_AVA/Typicals_0003

## Text Annotation 13 (SpecIF:Note)
- dcterms:description: Betrifft IST-Prozess. Zuküftig ist ein Nachfolgesystem geplant.

  BerlinLicht / Öffentl. Beleuchtung: BauSu wird heute anstatt HAM verwendet. Auch hier zukünftig ggf. ein neues System

## Text Annotation 14 (SpecIF:Note)
- dcterms:description: Vorschlag: Anforderungen aus anderen Fachbereichen in die Planung integrieren.

## Text Annotation 15 (SpecIF:Note)
- dcterms:description: iv-64

## Text Annotation 16 (SpecIF:Note)
- dcterms:description: Die Preise im Angebot können von den technisch konzipierten Kosten abweichen -> Interne Kosten sind abweichend von den Angebotspreisen (Kundenangebote).

## Text Annotation 17 (SpecIF:Note)
- dcterms:description: Anmerkung: Kostenschätzung (DIN276) wird hier grob mit Hilfe von Typicals erstellt. Die Feinplanung erfolgt im Schritt 16.

## Text Annotation 18 (SpecIF:Note)
- dcterms:description: User Story offen

## Text Annotation 19 (SpecIF:Note)
- dcterms:description: Typicals

## Text Annotation 20 (SpecIF:Note)
- dcterms:description: + Anschlusstermin
  + Baufreigabe (inkl. Kundenstammdaten)
  + HA-Skizzen
  + etc.

## Text Annotation 21 (SpecIF:Note)
- dcterms:description: User Story offen

## Text Annotation 22 (SpecIF:Note)
- dcterms:description: Typicals

## Text Annotation 23 (SpecIF:Note)
- dcterms:description: Typicals

## Zustände (SpecIF:Heading)

## Geschäftsprozesse (SpecIF:Heading)
- dcterms:type: SpecIF:BusinessProcesses

## Modellelemente (Glossar) (SpecIF:Heading)
- dcterms:type: SpecIF:Glossary

## Akteure (SpecIF:Heading)

## Zustände (SpecIF:Heading)

## Ereignisse (SpecIF:Heading)

## Kollektionen und Gruppen (SpecIF:Heading)

## 18:Kundenanfrage aufnehmen (FMC:Actor)
- dcterms:type: BPMN:userTask

## 19:Kundenanfrage bewerten (FMC:Actor)
- dcterms:type: BPMN:userTask

## 20:Netzauftrag anlegen (FMC:Actor)
- dcterms:type: BPMN:userTask
- dcterms:description: Für die Durchführung einer Netzmaßnahme wird ein entsprechender Netzauftrag in SAP NeMo angelegt.

## 21:Technisches Konzept erstellen (FMC:Actor)
- dcterms:type: BPMN:userTask

## 22:Kalkulation erstellen (FMC:Actor)
- dcterms:type: BPMN:task
- dcterms:description: + Kostenschätzung (DIN 276)

## 23:Angebot erstellen (FMC:Actor)
- dcterms:type: BPMN:userTask

## 24:Netzauftrag schließen (FMC:Actor)
- dcterms:type: BPMN:task

## 25:Fachbereiche abfragen/mitnehmen (FMC:Actor)
- dcterms:type: BPMN:userTask

## 26:Maßnahmen berücksichtigen und beauftragen (FMC:Actor)
- dcterms:type: BPMN:userTask

## Akteure (SpecIF:Heading)

## Angebotsblatt (FMC:State)
- dcterms:type: BPMN:dataObject

## Asset Service - Sonderkundenberater (SKB) (FMC:Actor)
- dcterms:type: SpecIF:Role

## Ereignisse (SpecIF:Heading)

## Forking Exclusive Gateway: Angebot vom Kunden angenommen? (FMC:Actor)
- dcterms:description: Evaluate the condidition and signal the respective event.
- dcterms:type: BPMN:exclusiveGateway

## Geschäftsprozesse (SpecIF:Heading)
- dcterms:type: SpecIF:BusinessProcesses

## intermediateCatchEvent (FMC:Event)
- dcterms:type: BPMN:intermediateCatchEvent

## Ja (FMC:Event)
- dcterms:type: SpecIF:Condition
- dcterms:description: Forking Exclusive Gateway: Angebot vom Kunden angenommen? → Ja

## Kundenanfrage MS 10kV (>2MVA) eingegangen (FMC:Event)
- dcterms:type: BPMN:startEvent

## Modellelemente (Glossar) (SpecIF:Heading)
- dcterms:type: SpecIF:Glossary

## Nein (FMC:Event)
- dcterms:type: SpecIF:Condition
- dcterms:description: Forking Exclusive Gateway: Angebot vom Kunden angenommen? → Nein

## NKT XRM (FMC:State)
- dcterms:type: BPMN:dataStore

## Sammelprojekt -MS/NS--Netzauftrag konzipieren-Netzauftrag für Sonderkunden konzipieren (FMC:Actor)
- dcterms:type: BPMN:participant

## SP_KV_MSNS_2B_Sammelprojekt-MSNS--Netzauftrag konzipieren-SKB (SpecIF:Diagram)
- SpecIF:Diagram: Model View:
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- dcterms:type: SpecIF:BusinessProcess
- dcterms:description: Der Sub-Prozess "Netzauftrag für Sonderkunden konzipieren" wird durch den Asset Service durchgeführt. Eingehende Kundenanfragen in der Mittelspannung werden durch den Sonderkundenberater aufgenommen und an die Netzkonzeption weitergegeben. Hier erfolgt die initiale Bewertung und die Anlage des Netzauftrags in SAP (NeMo). Anschließend wird das technische Konzept sowie die initiale Kalkulation erstellt. Basierend hierauf erstellt der Sonderkundenberater das Angebot für den Kunden. Zum Ende der Konzeption werden die anderen Fachbereiche zwecks Mitnahmen und gegebenenfalls tangierenden Projekten abgefragt. Die Ergebnisse fließen in das final konzipierte technische Konzept ein.

## Text Annotation 01 (SpecIF:Note)
- dcterms:description: * Leistungsanfrage
  * Geräte
  * Grundpläne
  * Leistungsbilanz (Datenblätter)
  * Lageplan
  * Anschlusspunkt
  * Adresse
  * HA-Skizzen (optional)
  * Kundenpläne
  + Bewertung

## Text Annotation 02 (SpecIF:Note)
- dcterms:description: + Netzauftrag für Netzmaßnahme anlegen
  Enthält:
  + Titel
  + Straße
  + Was wird gemacht?
  + Nummer (von NeMo) generiert
  + CS-Aufträge in NeMo
  + Maßnahmen (empfohlene Maßnahmen, kundenbedingte Maßnahmen, FM-Maßnahmen)
  + Auftragsnummer (5-stellig) zurück melden

## Text Annotation 03 (SpecIF:Note)
- dcterms:description: + Anschlussskizze (Visio, AutoCAD)
  + Bauzaun (NiS)
  + Plan = Netzkonzept (Kabel, Gebäude, Straßen)
  + Netzaufträge koordinieren
  + Maßnahmenempfehlungen einfließen lassen
  + FM/LWL-Konzept

## Text Annotation 04 (SpecIF:Note)
- dcterms:description: * Anschlussskizze (Visio, AutoCAD)
  * Bauzaun (NiS)
  * Plan = Netzkonzept (Kabel, Gebäude, Straßen)
  * Netzaufträge koordiniert
  * Maßnahmenempfehlungen einfließen lassen
  * FM/LWL-Konzept
  + Kostenschätzung (DIN 276)

## Text Annotation 05 (SpecIF:Note)
- dcterms:description: * Anschlussskizze (Visio, AutoCAD)
  * Bauzaun (NiS)
  * Plan = Netzkonzept (Kabel, Gebäude, Straßen)
  * Netzaufträge koordiniert
  * Maßnahmenempfehlungen einfließen lassen
  * FM-Konzept
  * Kostenschätzung (DIN 276)
  + Mitnahmen (Fernsteuerung/Automation)
  + Baufreigabe
  + Sanierungsmaßnahmen

## Text Annotation 06 (SpecIF:Note)
- dcterms:description: * Leistungsanfrage
  * Geräte
  * Grundpläne
  * Leistungsbilanz (Datenblätter)
  * Lageplan
  * Anschlusspunkt
  * Adresse
  * HA-Skizzen (optional)
  * Kundenpläne

## Text Annotation 07 (SpecIF:Note)
- dcterms:description: UST_AVA/Typicals_0001

## Text Annotation 08 (SpecIF:Note)
- dcterms:description: Typicals

## Text Annotation 09 (SpecIF:Note)
- dcterms:description: + Anschlusstermin
  + Baufreigabe (inkl. Kundenstammdaten)
  + HA-Skizzen

## Text Annotation 10 (SpecIF:Note)
- dcterms:description: iv-64

## Text Annotation 11 (SpecIF:Note)
- dcterms:description: User Story offen

## Text Annotation 12 (SpecIF:Note)
- dcterms:description: UST_AVA/Typicals_0002
  UST_AVA/Typicals_0003

## Text Annotation 13 (SpecIF:Note)
- dcterms:description: User Story offen

## Text Annotation 14 (SpecIF:Note)
- dcterms:description: Typicals

## Text Annotation 15 (SpecIF:Note)
- dcterms:description: Typicals

## Zustände (SpecIF:Heading)

## Geschäftsprozesse (SpecIF:Heading)
- dcterms:type: SpecIF:BusinessProcesses

## Modellelemente (Glossar) (SpecIF:Heading)
- dcterms:type: SpecIF:Glossary

## Akteure (SpecIF:Heading)

## Zustände (SpecIF:Heading)

## Ereignisse (SpecIF:Heading)

## Kollektionen und Gruppen (SpecIF:Heading)

## 27:Vollständigkeit der Unterlagen und Machbarkeit prüfen (FMC:Actor)
- dcterms:type: BPMN:userTask
- dcterms:description: Das technische Konzept aus der Konzeptionierung wird auf Vollständigkeit und Machbarkeit überprüft.
  Sofern die Prüfung negativ ausfällt wird an in diesem Prozessschritt das technische Konzept zurück zur Konzeptionierung gegeben um die notwendigen Korrekturen und Ergänzungen durchführen zu lassen.

## 28:Technisches Konzept nacharbeiten (FMC:Actor)
- dcterms:type: BPMN:userTask
- dcterms:description: Das bemängelte technische Konzept wird nachbearbeitet und zurück an die Planung gegeben.

## 29:Genehmigungsplan erstellen (FMC:Actor)
- dcterms:type: BPMN:userTask
- dcterms:description: Anfrage der Genehmigung über infreSt. (nur Sondernutzung und Leitungsverwaltung)
  Die folgenden Systeme werden zur Erstellung der Genehmigungsplanung benötigt:
  - NIS (Trimble)
  - LiveLink
  -Sachdatenportal
  - ECM (Doxis)
  - Alkis

## 30:Ausführungsplan erstellen (FMC:Actor)
- dcterms:type: BPMN:userTask

## 31:MuF kalkulieren und Budget prüfen (FMC:Actor)
- dcterms:type: BPMN:userTask
- dcterms:description: Es erfolgt eine Berechnung in AVA zur Kalkulation der MuFs. Im Anschluss wird überprüft ob noch ausreichend Budget vorhanden ist.

## 32:Budget nachfordern (FMC:Actor)
- dcterms:type: BPMN:userTask

## 33:Über zusätzliches Budget entscheiden (FMC:Actor)
- dcterms:type: BPMN:userTask

## 34:Ausschreibung begleiten oder Abruf aus Rahmenvertrag (FMC:Actor)
- dcterms:type: BPMN:userTask
- dcterms:description: Basierend auf einer Managementvorgabe (Auftragshöhe) wird festgelegt ob die benötigten Leistungen ausgeschrieben werden müssen oder aus einem Rahmenvertrag bezogen werden können.


  Für die Ausschreibung müssen Ausschreibungsunterlagen angefertigt werden.

## 35:Bauakte zusammenstellen und beauftragen (FMC:Actor)
- dcterms:type: BPMN:userTask

## Akteure (SpecIF:Heading)

## Alkis (FMC:State)
- dcterms:type: BPMN:dataStore

## Asset Service - Netzplaner (FMC:Actor)
- dcterms:type: SpecIF:Role

## Ereignisse (SpecIF:Heading)

## Forking Exclusive Gateway: Budget ausreichend? (FMC:Actor)
- dcterms:description: Evaluate the condidition and signal the respective event.
- dcterms:type: BPMN:exclusiveGateway

## Forking Exclusive Gateway: Prüfung bestanden? (FMC:Actor)
- dcterms:description: Evaluate the condidition and signal the respective event.
- dcterms:type: BPMN:exclusiveGateway

## Forking Exclusive Gateway: Zusätzliches Budget genehmigt? (FMC:Actor)
- dcterms:description: Evaluate the condidition and signal the respective event.
- dcterms:type: BPMN:exclusiveGateway

## Genehmigungen/Leitungsauskünfte erhalten (FMC:Event)
- dcterms:type: BPMN:intermediateCatchEvent

## Geschäftsprozesse (SpecIF:Heading)
- dcterms:type: SpecIF:BusinessProcesses

## infreSt (FMC:State)
- dcterms:type: BPMN:dataStore
- dcterms:description: Leitungsverwaltung
  + Genehmigungsplan (Baustellenatlas, Darstellung von Bauaktivitäten)
  EXTERNE Anwendung für verschiedene andere Medien (Gas/Abwasser etc.)

## Ja (FMC:Event)
- dcterms:type: SpecIF:Condition
- dcterms:description: Forking Exclusive Gateway: Budget ausreichend? → Ja

## Ja (FMC:Event)
- dcterms:type: SpecIF:Condition
- dcterms:description: Forking Exclusive Gateway: Zusätzliches Budget genehmigt? → Ja

## Joining Exclusive Gateway (FMC:Actor)
- dcterms:description: Wait for any one incoming branch to continue.
- dcterms:type: BPMN:exclusiveGateway

## Joining Exclusive Gateway (FMC:Actor)
- dcterms:description: Wait for any one incoming branch to continue.
- dcterms:type: BPMN:exclusiveGateway

## Modellelemente (Glossar) (SpecIF:Heading)
- dcterms:type: SpecIF:Glossary

## Nein (FMC:Event)
- dcterms:type: SpecIF:Condition
- dcterms:description: Forking Exclusive Gateway: Zusätzliches Budget genehmigt? → Nein

## Nein (FMC:Event)
- dcterms:type: SpecIF:Condition
- dcterms:description: Forking Exclusive Gateway: Budget ausreichend? → Nein

## Netzauftrag ist beauftragt (FMC:Event)
- dcterms:type: BPMN:endEvent

## Planung beendet (FMC:Event)
- dcterms:type: BPMN:endEvent

## Sammelprojekt-MS/NS--Netzauftrag planen (FMC:Actor)
- dcterms:type: BPMN:participant

## SP_KV_MSNS_3_Sammelprojekt-MSNS--Netzauftrag planen (SpecIF:Diagram)
- SpecIF:Diagram: Model View:
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- dcterms:type: SpecIF:BusinessProcess

## Text Annotation 01 (SpecIF:Note)
- dcterms:description: Leitungsverwaltung
  + Genehmigungsplan (Baustellenatlas, Darstellung von Bauaktivitäten)
  EXTERNE Anwendung für verschiedene andere Medien (Gas/Abwasser etc.)

## Text Annotation 02 (SpecIF:Note)
- dcterms:description: iv-54

## Text Annotation 03 (SpecIF:Note)
- dcterms:description: * Anschlussskizze (Visio, AutoCAD)
  * Bauzaun (NiS)
  * Plan = Netzkonzept (Kabel, Gebäude, Straßen)
  * Netzaufträge koordinieren
  * Maßnahmenempfehlungen einfließen lassen
  * FM-Konzept
  * Kostenberechnung (DIN 276)
  * Mitnahmen (Fernsteuerung/Automation)
  * Baufreigabe
  * Kundenpläne

  + Genehmigungsplan
  + Leitungsauskünfte und Genehmigungen
  + Ausführungsplan
  + Vertrag/Verträge mit AN

## Text Annotation 04 (SpecIF:Note)
- dcterms:description: Kostenübersicht/Deckblatt

## Text Annotation 05 (SpecIF:Note)
- dcterms:description: Adressaten:
  * Projektleiter / Planer
  * Bauleiter
  * Tiefbau-Firma
  * Montage-Firma
  * Montage-Sekundär-Firma (Fernmelde-,...)
  * Netzbetrieb

## Text Annotation 06 (SpecIF:Note)
- dcterms:description: + Zeichnung/en (Visio, AutoCAD)
  + NIS (Planebene)

## Text Annotation 07 (SpecIF:Note)
- dcterms:description: * Zeichnung/en (Visio, AutoCAD)
  * NIS (Planebene)
  + Kostenberechnung (DIN276)

## Text Annotation 08 (SpecIF:Note)
- dcterms:description: + Leistungskatalog

## Text Annotation 09 (SpecIF:Note)
- dcterms:description: UST_AVA/Typicals_0010

  UST_AVA/Typicals_0011
  UST_AVA/Typicals_0012
  UST_AVA/Typicals_0013
  UST_AVA/Typicals_0014
  UST_AVA/Typicals_0015

## Text Annotation 10 (SpecIF:Note)
- dcterms:description: Wie ist der Einkauf eingebunden und wie arbeitet er mit AVA bzw. wie erfolgt Datenübergabe zuküftig (SAP/AVA)?

## Text Annotation 11 (SpecIF:Note)
- dcterms:description: UST_AVA/Typicals_0004 - (aufteilen in mehrere User Stories)

## Text Annotation 12 (SpecIF:Note)
- dcterms:description: UST_AVA/Typicals_0005

## Weiter an Genehmigungsplanung (FMC:Event)
- dcterms:type: SpecIF:Condition
- dcterms:description: Forking Exclusive Gateway: Prüfung bestanden? → Weiter an Genehmigungsplanung

## Zurück an Konzeption (FMC:Event)
- dcterms:type: SpecIF:Condition
- dcterms:description: Forking Exclusive Gateway: Prüfung bestanden? → Zurück an Konzeption

## Zustände (SpecIF:Heading)

## Geschäftsprozesse (SpecIF:Heading)
- dcterms:type: SpecIF:BusinessProcesses

## Modellelemente (Glossar) (SpecIF:Heading)
- dcterms:type: SpecIF:Glossary

## Akteure (SpecIF:Heading)

## Zustände (SpecIF:Heading)

## Ereignisse (SpecIF:Heading)

## Kollektionen und Gruppen (SpecIF:Heading)

## 36:Bauakte prüfen (FMC:Actor)
- dcterms:type: BPMN:userTask

## 37:Bauakte nacharbeiten (FMC:Actor)
- dcterms:type: BPMN:userTask

## 38:Bedingungen vor Ort prüfen (FMC:Actor)
- dcterms:type: BPMN:userTask

## 39:Abruf aus Rahmenvertr. und/oder Ausschreibung durchführen (FMC:Actor)
- dcterms:type: BPMN:userTask

## 40:Baubeginn abstimmen (FMC:Actor)
- dcterms:type: BPMN:userTask
- dcterms:description: Auftrag bzw. Abruf

## 41:Ausführung überwachen (intern oder extern) (FMC:Actor)
- dcterms:type: BPMN:userTask

## 42:Kabelmontage beauftragen (FMC:Actor)
- dcterms:type: BPMN:userTask
- dcterms:description: Kabelanschlußunternehmer(extern) oder interne Monteure:
  - MS/NS
  - FM (Fernmeldearbeiten)

## 43:Aufmaß prüfen (FMC:Actor)
- dcterms:type: BPMN:userTask
- dcterms:description: LEB wird vom Bauunternehmer mit Rechnung eingereicht und über AVA beglichen.

## 44:Ist-Doku kontrollieren und an NIS weiterleiten & archivieren (FMC:Actor)
- dcterms:type: BPMN:userTask

## 45:Netzauftrag abschließen (FMC:Actor)
- dcterms:type: BPMN:task

## ADMS (FMC:State)
- dcterms:type: BPMN:dataStore

## Akteure (SpecIF:Heading)

## Asset Service - Bauleitung (FMC:Actor)
- dcterms:type: SpecIF:Role

## Asset Service - Planung (FMC:Actor)
- dcterms:type: SpecIF:Role

## ausgew. Firma/Firmen (FMC:State)
- dcterms:type: BPMN:dataObject

## Baustellen-Begehungs-Protokoll (FMC:State)
- dcterms:type: BPMN:dataObject
- dcterms:description: - per App, Web oder Zettel

## Dienstleister-Portal (FMC:State)
- dcterms:type: BPMN:dataStore

## Ereignisse (SpecIF:Heading)

## Felix (FMC:State)
- dcterms:type: BPMN:dataStore

## Forking Exclusive Gateway (FMC:Actor)
- dcterms:description: Evaluate the condidition and signal the respective event.
- dcterms:type: BPMN:exclusiveGateway

## Forking Exclusive Gateway: Bauausführung möglich? (FMC:Actor)
- dcterms:description: Evaluate the condidition and signal the respective event.
- dcterms:type: BPMN:exclusiveGateway

## Forking Exclusive Gateway: Prüfung bestanden? (FMC:Actor)
- dcterms:description: Evaluate the condidition and signal the respective event.
- dcterms:type: BPMN:exclusiveGateway

## Forking Inclusive Gateway: Ist Kabelmontage und/oder Tiefbau erforderlich? (FMC:Actor)
- dcterms:description: Evaluate all condiditions and signal the respective events.
- dcterms:type: BPMN:inclusiveGateway

## Geschäftsprozesse (SpecIF:Heading)
- dcterms:type: SpecIF:BusinessProcesses

## Ja (FMC:Event)
- dcterms:type: SpecIF:Condition
- dcterms:description: Forking Exclusive Gateway: Bauausführung möglich? → Ja

## Ja (FMC:Event)
- dcterms:type: SpecIF:Condition
- dcterms:description: Forking Exclusive Gateway: Prüfung bestanden? → Ja

## Joining Exclusive Gateway (FMC:Actor)
- dcterms:description: Wait for any one incoming branch to continue.
- dcterms:type: BPMN:exclusiveGateway

## Joining Inclusive Gateway (FMC:Actor)
- dcterms:description: Wait for all active incoming branches to continue.
- dcterms:type: BPMN:inclusiveGateway

## Kabelmontage (FMC:Event)
- dcterms:type: SpecIF:Condition
- dcterms:description: Forking Inclusive Gateway: Ist Kabelmontage und/oder Tiefbau erforderlich? → Kabelmontage

## Modellelemente (Glossar) (SpecIF:Heading)
- dcterms:type: SpecIF:Glossary

## Nein (FMC:Event)
- dcterms:type: SpecIF:Condition
- dcterms:description: Forking Exclusive Gateway: Bauausführung möglich? → Nein

## Nein (FMC:Event)
- dcterms:type: SpecIF:Condition
- dcterms:description: Forking Exclusive Gateway: Prüfung bestanden? → Nein

## Netzauftrag ausgeführt (FMC:Event)
- dcterms:type: BPMN:endEvent

## Netzveränderung (FMC:State)
- dcterms:type: BPMN:dataObject

## PlanIT (NIS) (FMC:State)
- dcterms:type: BPMN:dataStore

## Sammelprojekt-MS/NS--Netzauftrag ausführen (FMC:Actor)
- dcterms:type: BPMN:participant

## SP_KV_MSNS_4_Sammelprojekt-MSNS--Netzauftrag ausführen (SpecIF:Diagram)
- SpecIF:Diagram: Model View:
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- dcterms:type: SpecIF:BusinessProcess
- dcterms:description: Der Sub-Prozess "Netzauftrag ausführen" wird durch den Asset Service (Bauleitung) durchgeführt. Nach einer initialen Prüfung der Bauakte werden die Bedingungen vor Ort durch eine Begehung final geprüft bevor der Bau starten kann. Die für den Bau benötigten Ressourcen werden über Abrufe aus Rahmenverträgen und/oder Ausschreibungen beschafft. Im Anschluss wird der Baubeginn mit den ausgewählten Firmen abgestimmt. Während des Baus erfolgt eine fortlaufende Überwachung und Dokumentation mittels Baustellenbegehungsprotokollen. Für die Abrechnung der bauausführenden Firmen werden die Aufmaße geprüft und Leistungserfassungsblätter bestätigt. Am Ende des Prozesses wird die Ist-Dokumentation kontrolliert, im NIS gepflegt und archiviert, bevor die Bauakte abgeschlossen werden kann.

## Text Annotation 01 (SpecIF:Note)
- dcterms:description: Parallel zum Prozess:
  - QM-Prüfung dokumentieren (im FFM ablegen)
  - Budgetüberwachung
  - Prognosen erstellen

  Materiallogistiker:
  - Bauleitung geht davon aus, dass Material verfügbar ist.

## Text Annotation 02 (SpecIF:Note)
- dcterms:description: Übersicht Rahmenverträge

## Text Annotation 03 (SpecIF:Note)
- dcterms:description: Felix-> SAP->Dienstleisterportal

  (Kleine Anbieter gehen über Web (DL-Portal) und Abruf-Bestellung.
  GAEB-Standard optional, keinesfalls zwingend, da kleine Firmen damit nicht umgehen können.)

## Text Annotation 04 (SpecIF:Note)
- dcterms:description: - per App, Web oder Zettel

## Text Annotation 05 (SpecIF:Note)
- dcterms:description: Die Bestätigung der LEBs löst in SAP eine Gutschrift aus. Dies erfolgt automatisch im Sub-Ledger-Prozess.

## Text Annotation 06 (SpecIF:Note)
- dcterms:description: UST_AVA/Typicals_0005
  UST_AVA/Typicals_0010

## Text Annotation 07 (SpecIF:Note)
- dcterms:description: UST_AVA/Typicals_0011
  UST_AVA/Typicals_0012
  UST_AVA/Typicals_0013
  UST_AVA/Typicals_0014
  UST_AVA/Typicals_0015

## Text Annotation 08 (SpecIF:Note)
- dcterms:description: UST_AVA/Typicals_0016
  UST_AVA/Typicals_0017

## Tiefbau (FMC:Event)
- dcterms:type: SpecIF:Condition
- dcterms:description: Forking Inclusive Gateway: Ist Kabelmontage und/oder Tiefbau erforderlich? → Tiefbau

## Vermessungszeichnung (Aufmaß) (FMC:State)
- dcterms:type: BPMN:dataObject

## Zurück an Konzeption/Planung (FMC:Event)
- dcterms:type: BPMN:endEvent

## Zustände (SpecIF:Heading)

## Geschäftsprozesse (SpecIF:Heading)
- dcterms:type: SpecIF:BusinessProcesses

## Modellelemente (Glossar) (SpecIF:Heading)
- dcterms:type: SpecIF:Glossary

## Akteure (SpecIF:Heading)

## Zustände (SpecIF:Heading)

## Ereignisse (SpecIF:Heading)

## Kollektionen und Gruppen (SpecIF:Heading)

## AVA-Typicals (User-Stories) (SpecIF:Outline)

## AVA_Typicals (SpecIF:Heading)

## UST_AVA/Typicals_0001 - Bauvorhaben (Projekt) anlegen (SpecIF:UserStory)
- dcterms:identifier: UST_AVA/Typicals_0001
- dcterms:description: Als Projektleiter möchte ich ein Bauvorhaben im AVA-Programm anlegen um dort eine Mengen- und Kostenkalkulation durchführen zu können.
- SpecIF:Priority: 1_hoch
- dcterms:modified: 2020-03-31T22:00:00.000Z
- dcterms:creator: Herr Max Brugger
- dcterms:subject: C2

## UST_AVA/Typicals_0002 - LV konfigurieren (SpecIF:UserStory)
- dcterms:identifier: UST_AVA/Typicals_0002
- dcterms:description: Als Teilprojektleiter möchte das LV konkretisieren/ kofiguriegen um anschließend eine Mengen und Kostenberechnung durchzuführen.
- SpecIF:Priority: 1_hoch
- dcterms:modified: 2020-03-31T22:00:00.000Z
- dcterms:creator: Herr Max Brugger
- dcterms:subject: C3

## UST_AVA/Typicals_0003 - Kostenzuordnung festlegen (SpecIF:UserStory)
- dcterms:identifier: UST_AVA/Typicals_0003
- dcterms:description: Als Teilprojektleiter möchte ich die Kostenzuordnung festlegen um Leistungen nach Betriebsmittelgruppen (Aufw., Inv., und Jahresscheiben) zu planen. (Treiber sind Anlagengruppen nach BNetzA)
- SpecIF:Priority: 1_hoch
- dcterms:modified: 2020-03-31T22:00:00.000Z
- dcterms:creator: Herr Max Brugger
- dcterms:subject: C5

## UST_AVA/Typicals_0004 - Leistungsbeschreibung spezifizieren (SpecIF:UserStory)
- dcterms:identifier: UST_AVA/Typicals_0004
- dcterms:description: Als Teilprojektleiter möchte ich die Leistungsbeschreibungen spezifizieren um …
  Hinweis: Ein "Anpassungskultur" wiederspricht einer weitestgehend Standardisierung durch Typicals.
  
  Hinweis: Aktuell bei MSNS 3 Prozessschritten zugeordnet -> User Stories verfeinern und nur eine User Story zu einer Task zuordnen.
- SpecIF:Priority: 1_hoch
- dcterms:modified: 2020-03-31T22:00:00.000Z
- dcterms:creator: Herr Felix Bath
- dcterms:subject: C6

## UST_AVA/Typicals_0005 - Abrufbestellung aus RV anlegen, Bestellanforderungen zum RV anlegen, Normalbestellung anlegen (SpecIF:UserStory)
- dcterms:identifier: UST_AVA/Typicals_0005
- dcterms:description: Als Projektleiter/Teilprojektleiter möchte ich die Anforderung einer Bestellung an den Einkauf übergeben (Banf1) um den Beschaffungsprozess anzustoßen.
  
  IR04: Wertgrenzen beachten -> In Requirements prüfen
- SpecIF:Priority: 1_hoch
- dcterms:modified: 2020-03-31T22:00:00.000Z
- dcterms:creator: Herr Felix Bath
- dcterms:subject: C7.1/C7.2/C7.3

## UST_AVA/Typicals_0006 - Selektierte Informationen mit Dritten (Bietern) austauschen (SpecIF:UserStory)
- dcterms:identifier: UST_AVA/Typicals_0006
- dcterms:description: Als Einkäufer möchte ich selektierte Informationen mit Bietern austauschen um die bestmögliche Auswahl eines Vertragspartners sicherzustellen. Die Übergabe der Daten soll Medienbruchfrei erfolgen.
  
  Details: Für den Einkaufsprozess muss es die Möglichkeit der Ausgabe der Leistungsverzeichnisse im Excel-Format (alle Formate) geben.
- SpecIF:Priority: 1_hoch
- dcterms:modified: 2020-03-31T22:00:00.000Z
- dcterms:creator: Herr Felix Bath
- dcterms:subject: C8

## UST_AVA/Typicals_0007 - Angebote vergleichen (SpecIF:UserStory)
- dcterms:identifier: UST_AVA/Typicals_0007
- dcterms:description: Als … möchte ich Angebote erfassen, sichern und auswerten sowie verhandelte Preisen im Preisspiegel einsehen um…
- SpecIF:Priority: 1_hoch
- dcterms:modified: 2020-03-31T22:00:00.000Z
- dcterms:creator: Herr Felix Bath
- dcterms:subject: C9

## UST_AVA/Typicals_0008 - Vergabevertag vorbereiten (SpecIF:UserStory)
- dcterms:identifier: UST_AVA/Typicals_0008
- dcterms:description: Als … möchte ich Rahmenverträge in AVA einspielen können um diese hier jederzeit einsehen zu können. Die Rahmenverträge müssen dem Projetleiter im AVA angezeigt werden.
  
  Details: Rahmenverträge müssen im AVA automatisiert über eine Schnittstelle durch SNB Mitarbeiter einspielbar sein.
- SpecIF:Priority: 1_hoch
- dcterms:modified: 2020-03-31T22:00:00.000Z
- dcterms:creator: Herr Felix Bath
- dcterms:subject: C10

## UST_AVA/Typicals_0009 - Vergabevertrag abschließen (SpecIF:UserStory)
- dcterms:identifier: UST_AVA/Typicals_0009
- dcterms:description: Als... möchte ich ... um ...
  Nach der Vergabe werden in dem SAP System ein oder mehrere Verträge mit den bepreisten Leistungspositionen durch den Einkäufer angelegt.Diese Verträge müssen im AVA-Tool dem Projektleiter zur Kalkulation und Beauftragung mittels Abrufbestellungen zur Verfügung stehen.
- SpecIF:Priority: 1_hoch
- dcterms:modified: 2020-03-31T22:00:00.000Z
- dcterms:creator: Herr Felix Bath
- dcterms:subject: C11

## UST_AVA/Typicals_0010 - Vertragsfirmen beauftragen (SpecIF:UserStory)
- dcterms:identifier: UST_AVA/Typicals_0010
- dcterms:description: Als... möchte ich ... um …
- SpecIF:Priority: 1_hoch
- dcterms:modified: 2020-03-31T22:00:00.000Z
- dcterms:creator: Herr Felix Bath
- dcterms:subject: C12

## UST_AVA/Typicals_0011 - IST-Leistungen durch Auftragnehmer erfassen (SpecIF:UserStory)
- dcterms:identifier: UST_AVA/Typicals_0011
- dcterms:description: Als Bauführer möchte ich das Aufmaß prüfen um die erbrachten Leistungen zu dokumentieren.
- SpecIF:Priority: 1_hoch
- dcterms:modified: 2020-03-31T22:00:00.000Z
- dcterms:creator: Herr Thomas Streubel
- dcterms:subject: C15

## UST_AVA/Typicals_0012 - Aufmaß / IST-Leistung durch AG prüfen (SpecIF:UserStory)
- dcterms:identifier: UST_AVA/Typicals_0012
- dcterms:description: Als Bauführer möchte ich das Aufmaß prüfen um die erbrachten Leistungen zu dokumentieren.
- SpecIF:Priority: 1_hoch
- dcterms:modified: 2020-03-31T22:00:00.000Z
- dcterms:creator: Herr Thomas Streubel
- dcterms:subject: C16

## UST_AVA/Typicals_0013 - IST-Leistungen durch AN bestätigen / abnehmen (SpecIF:UserStory)
- dcterms:identifier: UST_AVA/Typicals_0013
- dcterms:description: Als Bauführer möchte ich das Aufmaß prüfen um die erbrachten Leistungen zu dokumentieren.
- SpecIF:Priority: 1_hoch
- dcterms:modified: 2020-03-31T22:00:00.000Z
- dcterms:creator: Herr Thomas Streubel
- dcterms:subject: C17

## UST_AVA/Typicals_0014 - Rechnungsprüfung (SpecIF:UserStory)
- dcterms:identifier: UST_AVA/Typicals_0014
- dcterms:description: Als Bauführer möchte ich das Aufmaß prüfen um die erbrachten Leistungen zu dokumentieren.
- SpecIF:Priority: 1_hoch
- dcterms:modified: 2020-03-31T22:00:00.000Z
- dcterms:creator: Herr Thomas Streubel
- dcterms:subject: C18

## UST_AVA/Typicals_0015 - Zahlvorgang anstoßen + bearbeiten (SpecIF:UserStory)
- dcterms:identifier: UST_AVA/Typicals_0015
- dcterms:description: Als Bauführer möchte ich das Aufmaß prüfen um die erbrachten Leistungen zu dokumentieren.
- SpecIF:Priority: 1_hoch
- dcterms:modified: 2020-03-31T22:00:00.000Z
- dcterms:creator: Herr Thomas Streubel
- dcterms:subject: C19

## UST_AVA/Typicals_0016 - Kosten/Leistungs-SOLL-IST-Abgleich durchführen (SpecIF:UserStory)
- dcterms:identifier: UST_AVA/Typicals_0016
- dcterms:description: Als Projektleiter möchte ich den Soll/Ist Abgleich nach dem Projektabschluss durchführen um Lessons learned zu generieren und für diese Folgeprojekte bereitzustellen.
- SpecIF:Priority: 1_hoch
- dcterms:modified: 2020-03-31T22:00:00.000Z
- dcterms:creator: Herr Thomas Kiwus
- dcterms:subject: C20

## UST_AVA/Typicals_0017 - Auswertkriterien festlegen (SpecIF:UserStory)
- dcterms:identifier: UST_AVA/Typicals_0017
- dcterms:description: Als Projektleiter möchte ich den Soll/Ist Abgleich nach dem Projektabschluss durchführen um Lessons learned zu generieren und für diese Folgeprojekte bereitzustellen.
- SpecIF:Priority: 1_hoch
- dcterms:modified: 2020-03-31T22:00:00.000Z
- dcterms:creator: Herr Thomas Kiwus
- dcterms:subject: C21

## UST_AVA/Typicals_0018 - Titel (SpecIF:UserStory)
- dcterms:identifier: UST_AVA/Typicals_0018
- dcterms:description: Als Asset-Manager möchte ich ein Typical (Projekttyp+Projektkategorie) auswählen um ein Grundkonzept für meine Planung zu erhalten.
- SpecIF:Priority: 1_hoch
- dcterms:modified: 2020-04-13T22:00:00.000Z
- dcterms:creator: Herr Thomas Kiwus

## UST_AVA/Typicals_0019 - Titel (SpecIF:UserStory)
- dcterms:identifier: UST_AVA/Typicals_0019
- dcterms:description: Als Asset-Manager erstelle ich Projektvarianten mit Hilfe von verschiedenen Typicals um die Kostenkalkulation zu vereinfachen.
- SpecIF:Priority: 1_hoch
- dcterms:modified: 2020-04-13T22:00:00.000Z
- dcterms:creator: Herr Thomas Kiwus

## UST_AVA/Typicals_0020 - Titel (SpecIF:UserStory)
- dcterms:identifier: UST_AVA/Typicals_0020
- dcterms:description: Ich bin Projektleiter gemäß meines zuvor kalkulierten Tiefbauabschnittes  eine Tiefbaufirma über einen RV abrufen können.
- SpecIF:Priority: 1_hoch
- dcterms:modified: 2020-04-13T22:00:00.000Z

## UST_AVA/Typicals_0021 - Titel (SpecIF:UserStory)
- dcterms:identifier: UST_AVA/Typicals_0021
- dcterms:description: Ich bin Bauführer und möchte Aufmaße digital von dem Auftragnehmer eingespielt bekommen, diese ggf. korrigieren und freigeben können, um ein ausdrucken zu vermeiden und einen durchgehenden / dokumentierbaren  Abrechnungsprozess zu erhalten.
- SpecIF:Priority: 1_hoch
- dcterms:modified: 2020-04-13T22:00:00.000Z

## UST_AVA/Typicals_0022 - Projektspezifisches Leistungsverzeichnis erstellen (SpecIF:UserStory)
- dcterms:identifier: UST_AVA/Typicals_0022
- dcterms:description: Als Teilprojektleiter möchte ich ausgehend von einer Vorlage ein projektspezifisches Leistungsverzeichnis erstellen um eine aussagekräftige Ausschreibungsunterlage bereitstellen zu können. Im Ausnahmefall soll ein Leistungsverzeichnis auch von Grund auf aufgebaut werden können.
- SpecIF:Priority: 1_hoch
- dcterms:modified: 2020-04-13T22:00:00.000Z
- dcterms:creator: Herr Thomas Streubel
- dcterms:subject: C6

## UST_AVA/Typicals_0023 - Suchfunktion in TBs und Richtlinien (SpecIF:UserStory)
- dcterms:identifier: UST_AVA/Typicals_0023
- dcterms:description: Als Teilprojektleiter möchte ich durch eine leistungsfähige Suche die relevanten TBs und Richtlinien finden um den ausführenden Firmen die technische Anforderungen und ggf. Anleitungen an die Hand zu geben.
- SpecIF:Priority: 1_hoch
- dcterms:modified: 2020-04-13T22:00:00.000Z
- dcterms:creator: Herr Thomas Streubel
- dcterms:subject: C6

## Geschäftsprozesse (SpecIF:Heading)
- dcterms:type: SpecIF:BusinessProcesses

## Modellelemente (Glossar) (SpecIF:Heading)
- dcterms:type: SpecIF:Glossary

## Akteure (SpecIF:Heading)

## Zustände (SpecIF:Heading)

## Ereignisse (SpecIF:Heading)

## Kollektionen und Gruppen (SpecIF:Heading)

## AVA-Typicals (Anforderungen) (SpecIF:Outline)

## AVA_Typicals (SpecIF:Heading)

## REQ_AVA/Typicals_100 - 'Titel' (IREB:Requirement)
- dcterms:identifier: REQ_AVA/Typicals_100
- dcterms:subject: C12
- dcterms:description: Darstellung von Zahlplänen im Terminplan einer bestimmten Maßnahme und eines gesamten Loses
  ggf. über SNAP
- IREB:RequirementType: Funktion
- SpecIF:Priority: 1_hoch
- dcterms:modified: 2020-04-01T22:00:00.000Z

## REQ_AVA/Typicals_101 - 'Titel' (IREB:Requirement)
- dcterms:identifier: REQ_AVA/Typicals_101
- dcterms:subject: C21
- dcterms:description: Mit der Investitionsentscheidung (IE) (Ab der Projektphase Grobplanung) ist quartalsweise durch den AS eine Prognose (Qualität, Termine, Kosten) durchzuführen. Diese hat mit Einführung des SNB-übergreifenden AVA-Programms/Leistungskalkulationstool auf Leistungsebene zu erfolgen. Die Kosten resultieren aus der Leistung in Bezug zu den Terminen.
- IREB:RequirementType: Funktion
- SpecIF:Priority: 1_hoch
- dcterms:modified: 2020-04-01T22:00:00.000Z

## REQ_AVA/Typicals_102 - 'Titel' (IREB:Requirement)
- dcterms:identifier: REQ_AVA/Typicals_102
- dcterms:subject: C11
- dcterms:description: Nach erfolgter Vergabe und Übermittlung der bepreisten Leistungsverzeichnissen, dürfen diese nicht mehr verändert werden.
- IREB:RequirementType: Funktion
- SpecIF:Priority: 1_hoch
- dcterms:modified: 2020-04-01T22:00:00.000Z

## REQ_AVA/Typicals_103 - 'Titel' (IREB:Requirement)
- dcterms:identifier: REQ_AVA/Typicals_103
- dcterms:subject: C3
- dcterms:description: automatisches (digitales) Erstellen von Text-LV's anhand von Leistungspositionen welche die funktionalen Ausschreibungstexte ersetzen
- IREB:RequirementType: Funktion
- SpecIF:Priority: 1_hoch
- dcterms:modified: 2020-04-01T22:00:00.000Z

## REQ_AVA/Typicals_104 - 'Titel' (IREB:Requirement)
- dcterms:identifier: REQ_AVA/Typicals_104
- dcterms:subject: C6
- dcterms:description: Anforderung muss durch TP SNAP definiert werden
- IREB:RequirementType: Funktion
- SpecIF:Priority: 1_hoch
- dcterms:modified: 2020-04-01T22:00:00.000Z

## REQ_AVA/Typicals_105 - 'Titel' (IREB:Requirement)
- dcterms:identifier: REQ_AVA/Typicals_105
- dcterms:subject: C8
- dcterms:description: siehe Punkt 91
- IREB:RequirementType: Funktion
- SpecIF:Priority: 1_hoch
- dcterms:modified: 2020-04-01T22:00:00.000Z

## REQ_AVA/Typicals_107 - 'Titel' (IREB:Requirement)
- dcterms:identifier: REQ_AVA/Typicals_107
- dcterms:subject: C3
- dcterms:description: Im AVA-Programm/Leistungskalkulationstool müssen auf LV-Positionsebene die "direkten Kosten" abgebildet werden. Nachgelagert werden aus den "direkten Kosten" (außerhalb vom AVA-Programm/Leistungskalkulationstool) die "Bereichskosten (BeKo)" und "Projektkosten" (mit Umlagen und Zuschlägen).
- IREB:RequirementType: Funktion
- SpecIF:Priority: 1_hoch
- dcterms:modified: 2020-04-01T22:00:00.000Z

## REQ_AVA/Typicals_108 - 'Titel' (IREB:Requirement)
- dcterms:identifier: REQ_AVA/Typicals_108
- dcterms:subject: C8
- dcterms:description: Leistungsverzeichnisse müssen in verschieden Formate dem Bieter zur Verfügung gestellt werden können. (Excel, GAEB usw.)
- IREB:RequirementType: Funktion
- SpecIF:Priority: 1_hoch
- dcterms:modified: 2020-04-01T22:00:00.000Z

## REQ_AVA/Typicals_109 - 'Titel' (IREB:Requirement)
- dcterms:identifier: REQ_AVA/Typicals_109
- dcterms:subject: C19
- dcterms:description: Formular zur Zahlungsempfehlung an Kunden
- IREB:RequirementType: Funktion
- SpecIF:Priority: 1_hoch
- dcterms:modified: 2020-04-01T22:00:00.000Z

## REQ_AVA/Typicals_110 - 'Titel' (IREB:Requirement)
- dcterms:identifier: REQ_AVA/Typicals_110
- dcterms:subject: C6
- dcterms:description: siehe Punkt 82.2 (nur strukturelle Anpassungen keine inhaltliche-/ preisliche Anpassung)
- IREB:RequirementType: Funktion
- SpecIF:Priority: 1_hoch
- dcterms:modified: 2020-04-01T22:00:00.000Z

## REQ_AVA/Typicals_114 - 'Titel' (IREB:Requirement)
- dcterms:identifier: REQ_AVA/Typicals_114
- dcterms:subject: C6
- dcterms:description: siehe 82.2, 114
  - Bearbeiten und Verschieben von Positionen und LV-Losen durch jeden Projektverantwortlichen (Berechtigungsrolle) möglich
  
  -> Löschen von jeglichen Daten nur durch Key-User = Berechtigungskonzept
- IREB:RequirementType: Funktion
- SpecIF:Priority: 1_hoch
- dcterms:modified: 2020-04-01T22:00:00.000Z

## REQ_AVA/Typicals_115 - 'Titel' (IREB:Requirement)
- dcterms:identifier: REQ_AVA/Typicals_115
- dcterms:subject: C2
- dcterms:description:
  1. Bearbeitung/Anpassung/Erweiterung der Kalkulationstabellen (Betriebsmittel, Betriebsmittelpakete (LV-Positionen), Betriebsmittelgruppen und Typicals) durch Endanwender
  2. Bereitstellung einer Vorlage für die Bearbeitung
- IREB:RequirementType: Funktion
- SpecIF:Priority: 1_hoch
- dcterms:modified: 2020-04-01T22:00:00.000Z

## REQ_AVA/Typicals_117 - 'Titel' (IREB:Requirement)
- dcterms:identifier: REQ_AVA/Typicals_117
- dcterms:subject: C3
- dcterms:description: Die zugehörige Betriebsmittelgruppe, Kostenart (Invest/Aufwand/Demontage) und Monats-/Jahresscheibe muss je LV-Position hinterlegt bzw. eindeutig verknüpft werden.
- IREB:RequirementType: Funktion
- SpecIF:Priority: 1_hoch
- dcterms:modified: 2020-04-01T22:00:00.000Z

## REQ_AVA/Typicals_118 - 'Titel' (IREB:Requirement)
- dcterms:identifier: REQ_AVA/Typicals_118
- dcterms:subject: C21
- IREB:RequirementType: Funktion
- SpecIF:Priority: 1_hoch
- dcterms:modified: 2020-04-01T22:00:00.000Z

## REQ_AVA/Typicals_119 - 'Titel' (IREB:Requirement)
- dcterms:identifier: REQ_AVA/Typicals_119
- dcterms:subject: C3
- dcterms:description: BIM- Kompatibilität
- IREB:RequirementType: Funktion
- SpecIF:Priority: 1_hoch
- dcterms:modified: 2020-04-01T22:00:00.000Z

## REQ_AVA/Typicals_12 - 'Titel' (IREB:Requirement)
- dcterms:identifier: REQ_AVA/Typicals_12
- dcterms:subject: C2
- dcterms:description: Kalkulation je Betriebsmittelpaket (LV-Position) auf Basis von einzelnen, durch die PL ausgewählten, Projekten.
- IREB:RequirementType: Funktion
- SpecIF:Priority: 1_hoch
- dcterms:modified: 2020-04-01T22:00:00.000Z

## REQ_AVA/Typicals_122 - 'Titel' (IREB:Requirement)
- dcterms:identifier: REQ_AVA/Typicals_122
- dcterms:subject: C3
- dcterms:description: Einzelprojekte,
  Projekte mit mehreren Einzel-LV's,
  Teilprojekte mit Losen
  möglich
- IREB:RequirementType: Funktion
- SpecIF:Priority: 1_hoch
- dcterms:modified: 2020-04-01T22:00:00.000Z

## REQ_AVA/Typicals_124 - 'Titel' (IREB:Requirement)
- dcterms:identifier: REQ_AVA/Typicals_124
- dcterms:subject: C3
- dcterms:description: Zusammensetzung der Preise aus Kalkulationselemente und manuelle Ergänzungen
- IREB:RequirementType: Funktion
- SpecIF:Priority: 1_hoch
- dcterms:modified: 2020-04-01T22:00:00.000Z

## REQ_AVA/Typicals_125 - 'Titel' (IREB:Requirement)
- dcterms:identifier: REQ_AVA/Typicals_125
- dcterms:subject: C6
- dcterms:description: Erstellen und Pflegen eines Stamm-LV 
  - Automatisches Einpflegen von aktuellen Preisen aus Ausschreibungen
- IREB:RequirementType: Funktion
- SpecIF:Priority: 1_hoch
- dcterms:modified: 2020-04-01T22:00:00.000Z

## REQ_AVA/Typicals_126 - 'Titel' (IREB:Requirement)
- dcterms:identifier: REQ_AVA/Typicals_126
- dcterms:subject: C6
- dcterms:description: Position zur Abrechnung von Gebühren auf Nachweis 1 zu 1 (Dummypreisposition) siehe 56
- IREB:RequirementType: Funktion
- SpecIF:Priority: 1_hoch
- dcterms:modified: 2020-04-01T22:00:00.000Z

## REQ_AVA/Typicals_128 - 'Titel' (IREB:Requirement)
- dcterms:identifier: REQ_AVA/Typicals_128
- dcterms:subject: C3
- dcterms:description: Zuweisung der LV-Positionen zu Jahresscheiben.
- IREB:RequirementType: Funktion
- SpecIF:Priority: 1_hoch
- dcterms:modified: 2020-04-01T22:00:00.000Z

## REQ_AVA/Typicals_130 - 'Titel' (IREB:Requirement)
- dcterms:identifier: REQ_AVA/Typicals_130
- dcterms:subject: C8
- dcterms:description: Nach Fertigstellung des LV kann dieses (inkl. eines Deckblattes) über die Reportfunktion als PDF- Dokument gespeichert werden
- IREB:RequirementType: Funktion
- SpecIF:Priority: 1_hoch
- dcterms:modified: 2020-04-01T22:00:00.000Z

## REQ_AVA/Typicals_133 - 'Titel' (IREB:Requirement)
- dcterms:identifier: REQ_AVA/Typicals_133
- dcterms:subject: C11
- dcterms:description: Nachlässen müssen während der Ausschreibung (Verhandlung) auf Positions- sowie Gesamt-LV-Ebene eingetragen und dargestellt werden können.
- IREB:RequirementType: Funktion
- SpecIF:Priority: 1_hoch
- dcterms:modified: 2020-04-01T22:00:00.000Z

## REQ_AVA/Typicals_135 - 'Titel' (IREB:Requirement)
- dcterms:identifier: REQ_AVA/Typicals_135
- dcterms:subject: C16
- dcterms:description: Soll - Ist-Vergleich (von Mengen zwischen Auftrag und Abrechnung [Fertigstellungsgrad pro Position])
- IREB:RequirementType: Funktion
- SpecIF:Priority: 1_hoch
- dcterms:modified: 2020-04-01T22:00:00.000Z

## REQ_AVA/Typicals_136 - 'Titel' (IREB:Requirement)
- dcterms:identifier: REQ_AVA/Typicals_136
- dcterms:subject: C18
- dcterms:description: Externer Zugang von Capgemini auf das AVA-Tool um die Rechnungsdaten/Rechnungsanhang?
  Oder Zugang auf Sharepoint zur Übergabe
- IREB:RequirementType: Funktion
- SpecIF:Priority: 1_hoch
- dcterms:modified: 2020-04-01T22:00:00.000Z

## REQ_AVA/Typicals_137 - 'Titel' (IREB:Requirement)
- dcterms:identifier: REQ_AVA/Typicals_137
- dcterms:subject: C19
- dcterms:description: siehe 189
- IREB:RequirementType: Funktion
- SpecIF:Priority: 1_hoch
- dcterms:modified: 2020-04-01T22:00:00.000Z

## REQ_AVA/Typicals_139 - 'Titel' (IREB:Requirement)
- dcterms:identifier: REQ_AVA/Typicals_139
- dcterms:subject: C16
- dcterms:description: (3.7.2)
  Mit Abnahme der Leistungserfassungsblätter (LEB) werden die IST-Kosten "eingefroren".
  Die Ist-Kosten setzen sich aus den im SAP gebuchten Kosten zusammen.
- IREB:RequirementType: Funktion
- SpecIF:Priority: 1_hoch
- dcterms:modified: 2020-04-01T22:00:00.000Z

## REQ_AVA/Typicals_140 - 'Titel' (IREB:Requirement)
- dcterms:identifier: REQ_AVA/Typicals_140
- dcterms:subject: C20
- dcterms:description: Dargestellt werden können, soll die Kostenentwicklung von der Projektplanung bis hin zur Abrechnung der Leistung:
  
  auf LV- Positionseben sowie über alle Betriebsmittelgruppen
- IREB:RequirementType: Funktion
- SpecIF:Priority: 1_hoch
- dcterms:modified: 2020-04-01T22:00:00.000Z

## REQ_AVA/Typicals_141 - 'Titel' (IREB:Requirement)
- dcterms:identifier: REQ_AVA/Typicals_141
- dcterms:subject: C6
- dcterms:description: Anforderung 168 wird getrennt betrachtet:
  168.a: Positionen müssen unabhängige externe und interne Stammnummern haben. 
  Intern = Leistungstext und Einheit hinterlegt, werden durch SAP vergeben 
  Extern = dient zur Abrechnung
  168.b.: Importfunktion muss vorhanden sein (z. B. Excel in AVA)
- IREB:RequirementType: Funktion
- SpecIF:Priority: 1_hoch
- dcterms:modified: 2020-04-01T22:00:00.000Z

## REQ_AVA/Typicals_143 - 'Titel' (IREB:Requirement)
- dcterms:identifier: REQ_AVA/Typicals_143
- dcterms:subject: C3
- dcterms:description: Die Anpassung einzelner Mengen kann direkt im LV auf Positionsebene erfolgen. Diese Änderung wirkt sich dann automatisch auf die Kostenermittlung aus.
- IREB:RequirementType: Funktion
- SpecIF:Priority: 1_hoch
- dcterms:modified: 2020-04-01T22:00:00.000Z

## REQ_AVA/Typicals_144 - 'Titel' (IREB:Requirement)
- dcterms:identifier: REQ_AVA/Typicals_144
- dcterms:subject: C3
- dcterms:description: Eine Darstellung nach Kostengruppen gem. DIN 276 muss möglich sein (Grundlage dafür sind Stammdaten aus dem SNB Leistungsbuchkatalog, dabei sind Zusatzpositionen ergänzbar und die Kategorien der DIN 276 einpflegbar.
- IREB:RequirementType: Funktion
- SpecIF:Priority: 1_hoch
- dcterms:modified: 2020-04-01T22:00:00.000Z

## REQ_AVA/Typicals_145 - 'Titel' (IREB:Requirement)
- dcterms:identifier: REQ_AVA/Typicals_145
- dcterms:subject: C12
- dcterms:description: siehe Punkt 100
- IREB:RequirementType: Funktion
- SpecIF:Priority: 1_hoch
- dcterms:modified: 2020-04-01T22:00:00.000Z

## REQ_AVA/Typicals_147 - 'Titel' (IREB:Requirement)
- dcterms:identifier: REQ_AVA/Typicals_147
- dcterms:subject: C3
- dcterms:description: Modellkalkulationen müssen in der Detailstufe 3 und 4 mit Detailabfragen (u.a. Anzahl Kabelsysteme) verfeinert werden können
- IREB:RequirementType: Funktion
- SpecIF:Priority: 1_hoch
- dcterms:modified: 2020-04-01T22:00:00.000Z

## REQ_AVA/Typicals_148 - 'Titel' (IREB:Requirement)
- dcterms:identifier: REQ_AVA/Typicals_148
- dcterms:subject: C8
- dcterms:description: siehe Punkt 130
- IREB:RequirementType: Funktion
- SpecIF:Priority: 1_hoch
- dcterms:modified: 2020-04-01T22:00:00.000Z

## REQ_AVA/Typicals_149 - 'Titel' (IREB:Requirement)
- dcterms:identifier: REQ_AVA/Typicals_149
- dcterms:subject: C3
- dcterms:description: Bei Investition und Ersatzinvestitionen müssen die neuen und demontierten Mengen an die Anlagenbuchhaltung übermittelt werden können.
- IREB:RequirementType: Funktion
- SpecIF:Priority: 1_hoch
- dcterms:modified: 2020-04-01T22:00:00.000Z

## REQ_AVA/Typicals_15 - 'Titel' (IREB:Requirement)
- dcterms:identifier: REQ_AVA/Typicals_15
- dcterms:subject: C2
- dcterms:description: Kalkulationen von Projekten müssen auf Basis der Betriebsmittelpakete kopiert werden können, um dadurch schneller neue Projekte zu kalkulieren
- IREB:RequirementType: Funktion
- SpecIF:Priority: 1_hoch
- dcterms:modified: 2020-04-01T22:00:00.000Z

## REQ_AVA/Typicals_151 - 'Titel' (IREB:Requirement)
- dcterms:identifier: REQ_AVA/Typicals_151
- dcterms:subject: C20
- dcterms:description: (Massen)Auswertung von Rahmenverträgen auf Positionsebene
- IREB:RequirementType: Funktion
- SpecIF:Priority: 1_hoch
- dcterms:modified: 2020-04-01T22:00:00.000Z

## REQ_AVA/Typicals_152 - 'Titel' (IREB:Requirement)
- dcterms:identifier: REQ_AVA/Typicals_152
- dcterms:subject: C3
- dcterms:description: Modellkalkulation soll auf Grundlage von Mittelpreisen voran gegangener Projekte erfolgen
- IREB:RequirementType: Funktion
- SpecIF:Priority: 1_hoch
- dcterms:modified: 2020-04-01T22:00:00.000Z

## REQ_AVA/Typicals_154 - 'Titel' (IREB:Requirement)
- dcterms:identifier: REQ_AVA/Typicals_154
- dcterms:subject: C3
- dcterms:description: Eine Kalkulation für Kabelprojekte über eine digitale Karte.
- IREB:RequirementType: Funktion
- SpecIF:Priority: 1_hoch
- dcterms:modified: 2020-04-01T22:00:00.000Z

## REQ_AVA/Typicals_156 - 'Titel' (IREB:Requirement)
- dcterms:identifier: REQ_AVA/Typicals_156
- dcterms:subject: C7.2
- dcterms:description: Bei der Erstellung der Ausschreib-Banf muss im AVA-Tool zum einen ein internes Budget und zum anderen ein Volumen für die Externe (dient zur Planung der Leistung für den Auftragnehmer) Ausschreibung ausgegeben werden können.
- IREB:RequirementType: Funktion
- SpecIF:Priority: 1_hoch
- dcterms:modified: 2020-04-01T22:00:00.000Z

## REQ_AVA/Typicals_158 - 'Titel' (IREB:Requirement)
- dcterms:identifier: REQ_AVA/Typicals_158
- dcterms:subject: C3
- dcterms:description: Aus dem Stammdaten-LV muss es möglich sein auf Kostengruppenebene - Typicalgruppen zusammenzufassen und als Grundkalkulation als Basis zu hinterlegen. Die Typicals müssen durch Veränderung der Basisdaten sich automatisch mit verändern (z.B. Preissteigerungen)
- IREB:RequirementType: Funktion
- SpecIF:Priority: 1_hoch
- dcterms:modified: 2020-04-01T22:00:00.000Z

## REQ_AVA/Typicals_159 - 'Titel' (IREB:Requirement)
- dcterms:identifier: REQ_AVA/Typicals_159
- dcterms:subject: C3
- dcterms:description: (3.3.14)
  Die Kalkulation erfolgt zu einem großen Teil mit Kalkulationsmodellen.
  Kalkulationsmodell bedeutet, dass anhand eines bestimmten Wertes an einer bestimmten Stelle im Kalkulationsmodell bestimmte Anteile anderer Preispositionen des Leistungsverzeichnisses herangezogen werden und nicht einzeln betrachtet werden müssen.
- IREB:RequirementType: Funktion
- SpecIF:Priority: 1_hoch
- dcterms:modified: 2020-04-01T22:00:00.000Z

## REQ_AVA/Typicals_160 - 'Titel' (IREB:Requirement)
- dcterms:identifier: REQ_AVA/Typicals_160
- dcterms:subject: C3
- dcterms:description: Kalkulationsmodell bedeutet, dass anhand eines bestimmten Wertes an einer bestimmten Stelle im Kalkulationsmodell bestimmte Anteile anderer Preispositionen des Leistungsverzeichnisses herangezogen werden und nicht einzeln betrachtet werden müssen.
- IREB:RequirementType: Funktion
- SpecIF:Priority: 1_hoch
- dcterms:modified: 2020-04-01T22:00:00.000Z

## REQ_AVA/Typicals_161 - 'Titel' (IREB:Requirement)
- dcterms:identifier: REQ_AVA/Typicals_161
- dcterms:subject: C15
- dcterms:description: Übernahme von Aufmaßen aus GAEB D11 oder Excel, Ansätze durch SNB korrigierbar, 
  nach Bestätigung Erstellung Prüfrechnung (Vertragspreise mit Aufmaßmengen)
- IREB:RequirementType: Funktion
- SpecIF:Priority: 1_hoch
- dcterms:modified: 2020-04-01T22:00:00.000Z

## REQ_AVA/Typicals_164 - 'Titel' (IREB:Requirement)
- dcterms:identifier: REQ_AVA/Typicals_164
- dcterms:subject: C7.2
- dcterms:description: entfällt
- IREB:RequirementType: Funktion
- SpecIF:Priority: 1_hoch
- dcterms:modified: 2020-04-01T22:00:00.000Z

## REQ_AVA/Typicals_165 - 'Titel' (IREB:Requirement)
- dcterms:identifier: REQ_AVA/Typicals_165
- dcterms:subject: C3
- dcterms:description: Die Ermittlung der Mengen erfolgt über eine Zuordnung der in der Auswahl herangezogenen Elemente und einer prozentualen/mengenmäßigen Ermittlung in den zusätzlichen Positionen. Die Komplexität lässt sich an dieser Stelle beliebig erweitern.
- IREB:RequirementType: Funktion
- SpecIF:Priority: 1_hoch
- dcterms:modified: 2020-04-01T22:00:00.000Z

## REQ_AVA/Typicals_165.1 - 'Titel' (IREB:Requirement)
- dcterms:identifier: REQ_AVA/Typicals_165.1
- dcterms:subject: C3
- dcterms:description: Die Einzelkalkulation ohne Kalkulationsmodell, auf Positionsebene muss möglich sein.
- IREB:RequirementType: Funktion
- SpecIF:Priority: 1_hoch
- dcterms:modified: 2020-04-01T22:00:00.000Z

## REQ_AVA/Typicals_165.3 - 'Titel' (IREB:Requirement)
- dcterms:identifier: REQ_AVA/Typicals_165.3
- dcterms:subject: C3
- dcterms:description: Bei einer Kalkulation mit einem Kalkulationsmodell muss die Aufgliederung in Einzelpositionen möglich sein.
- IREB:RequirementType: Funktion
- SpecIF:Priority: 1_hoch
- dcterms:modified: 2020-04-01T22:00:00.000Z

## REQ_AVA/Typicals_165.4 - 'Titel' (IREB:Requirement)
- dcterms:identifier: REQ_AVA/Typicals_165.4
- dcterms:subject: C3
- dcterms:description: Wird in einem Kalkulationsmodell auf eine nicht vorhandene Preisposition zugegriffen ist eine Fehlermeldung zu generieren.
- IREB:RequirementType: Funktion
- SpecIF:Priority: 1_hoch
- dcterms:modified: 2020-04-01T22:00:00.000Z

## REQ_AVA/Typicals_165.5 - 'Titel' (IREB:Requirement)
- dcterms:identifier: REQ_AVA/Typicals_165.5
- dcterms:subject: C3
- dcterms:description: Für die Kalkulation größerer Bauvorhaben muss es möglich sein, die Kalkulationen in mehrere kleinen Kalkulationen aufzuteilen, die auf einer höheren Ebene aggregiert dargestellt werden.
- IREB:RequirementType: Funktion
- SpecIF:Priority: 1_hoch
- dcterms:modified: 2020-04-01T22:00:00.000Z

## REQ_AVA/Typicals_165.6 - 'Titel' (IREB:Requirement)
- dcterms:identifier: REQ_AVA/Typicals_165.6
- dcterms:subject: C3
- dcterms:description: Es muss die Möglichkeit geben, für die Budgetplanung zukünftiger (Rahmen-)Verträge die Mengen aus inhaltlich gleichen LV-Positionen über verschiedene Muster-LV auswerten zu können.
- IREB:RequirementType: Funktion
- SpecIF:Priority: 1_hoch
- dcterms:modified: 2020-04-01T22:00:00.000Z

## REQ_AVA/Typicals_166 - 'Titel' (IREB:Requirement)
- dcterms:identifier: REQ_AVA/Typicals_166
- dcterms:subject: C5
- dcterms:description: Handelt es sich um einen einzelnen SAP-Auftrag ist die Aufteilungssumme mit 100 % vor zu belegen.
- IREB:RequirementType: Funktion
- SpecIF:Priority: 1_hoch
- dcterms:modified: 2020-04-01T22:00:00.000Z

## REQ_AVA/Typicals_166.1 - 'Titel' (IREB:Requirement)
- dcterms:identifier: REQ_AVA/Typicals_166.1
- dcterms:subject: C5
- dcterms:description: Die Verteilung der Kosten auf die einzelnen SAP-Aufträge erfolgt bei der Abnahme der LEBs im Business Workplace.
- IREB:RequirementType: Funktion
- SpecIF:Priority: 1_hoch
- dcterms:modified: 2020-04-01T22:00:00.000Z

## REQ_AVA/Typicals_166.2 - 'Titel' (IREB:Requirement)
- dcterms:identifier: REQ_AVA/Typicals_166.2
- dcterms:subject: C5
- dcterms:description: Es besteht die Möglichkeit die Auswertungen/ Ausschreibungs-LV´s mit Formeln in Standardformate(z.B. .xlsx-Datei) zu exportieren
- IREB:RequirementType: Funktion
- SpecIF:Priority: 1_hoch
- dcterms:modified: 2020-04-01T22:00:00.000Z

## REQ_AVA/Typicals_167 - 'Titel' (IREB:Requirement)
- dcterms:identifier: REQ_AVA/Typicals_167
- dcterms:subject: C17
- dcterms:description: Die Summen der einzelnen LEB sind in den zugeordneten CS-Aufträgen (auftragsscharf) zu addieren und im Abschnitt (Ebene3) im SAP (markierte Tabelle s. Anlage 14) darzustellen.
- IREB:RequirementType: Funktion
- SpecIF:Priority: 1_hoch
- dcterms:modified: 2020-04-01T22:00:00.000Z

## REQ_AVA/Typicals_167.1 - 'Titel' (IREB:Requirement)
- dcterms:identifier: REQ_AVA/Typicals_167.1
- dcterms:subject: C17
- dcterms:description: Mit der Endabnahme des LEB werden die gesamten Ist-Kosten "eingefroren", eine Änderung ist nicht mehr möglich.
- IREB:RequirementType: Funktion
- SpecIF:Priority: 1_hoch
- dcterms:modified: 2020-04-01T22:00:00.000Z

## REQ_AVA/Typicals_167.2 - 'Titel' (IREB:Requirement)
- dcterms:identifier: REQ_AVA/Typicals_167.2
- dcterms:subject: C17
- dcterms:description: Historisieren von Aufmaßen
- IREB:RequirementType: Funktion
- SpecIF:Priority: 1_hoch
- dcterms:modified: 2020-04-01T22:00:00.000Z

## REQ_AVA/Typicals_168 - 'Titel' (IREB:Requirement)
- dcterms:identifier: REQ_AVA/Typicals_168
- dcterms:subject: C6
- dcterms:description: Die LV-Positionen aus dem AVA-Tool (ID 168) sollen per "Knopfdruck" über eine Schnittstelle ins SAP übertragen und in SAP Leistungsstammsätze angelegt werden.
- IREB:RequirementType: Funktion
- SpecIF:Priority: 1_hoch
- dcterms:modified: 2020-04-01T22:00:00.000Z

## REQ_AVA/Typicals_169 - 'Titel' (IREB:Requirement)
- dcterms:identifier: REQ_AVA/Typicals_169
- dcterms:subject: C6
- dcterms:description: Nach Anlegen der Leistungsstammsätze gem. ID 169 muss die interne Leistungsnummer an das AVA-Tool zur jeweiligen LV-Position zurückgegeben werden.
- IREB:RequirementType: Funktion
- SpecIF:Priority: 1_hoch
- dcterms:modified: 2020-04-01T22:00:00.000Z

## REQ_AVA/Typicals_17 - 'Titel' (IREB:Requirement)
- dcterms:identifier: REQ_AVA/Typicals_17
- dcterms:subject: C21
- dcterms:description: Auswertung älterer Datenbestände (Kosten, Zeit, Leistungen je Plan/Prognose/IST)
- IREB:RequirementType: Funktion
- SpecIF:Priority: 1_hoch
- dcterms:modified: 2020-04-01T22:00:00.000Z

## REQ_AVA/Typicals_170 - 'Titel' (IREB:Requirement)
- dcterms:identifier: REQ_AVA/Typicals_170
- dcterms:subject: C6
- dcterms:description: Vorhandene LV-Positionen bzw. Leistungsstammsätze müssen verändert werden können (redaktionell) und mit SAP abgeglichen werden.
- IREB:RequirementType: Funktion
- SpecIF:Priority: 1_hoch
- dcterms:modified: 2020-04-01T22:00:00.000Z

## REQ_AVA/Typicals_171 - 'Titel' (IREB:Requirement)
- dcterms:identifier: REQ_AVA/Typicals_171
- dcterms:subject: C6
- dcterms:description: Wenn sich der Leistungsinhalt grob ändert, muss eine neue LV-Position durch Kopier- und Änderungsmöglichkeit im AVA-Tool mit einer eineindeutigen ext. Leistungsnummer angelegt werden können (gem. ID 168) und durch Übertragung ins SAP ein neuer Leistungsstammsatz mit neuer interner Leistungsnummer angelegt werden (gem. ID 169) und an das AVA-Tool zurückgegeben werden (gem. ID 170).
- IREB:RequirementType: Funktion
- SpecIF:Priority: 1_hoch
- dcterms:modified: 2020-04-01T22:00:00.000Z

## REQ_AVA/Typicals_172 - 'Titel' (IREB:Requirement)
- dcterms:identifier: REQ_AVA/Typicals_172
- dcterms:subject: C6
- dcterms:description: Aus den LV-Positionen (ID 168, 171, 172) werden Muster-Leistungsverzeichnisse nach Gewerken unterteilt im AVA-Tool erstellt.
- IREB:RequirementType: Funktion
- SpecIF:Priority: 1_hoch
- dcterms:modified: 2020-04-01T22:00:00.000Z

## REQ_AVA/Typicals_173 - 'Titel' (IREB:Requirement)
- dcterms:identifier: REQ_AVA/Typicals_173
- dcterms:subject: C6
- dcterms:description: Stammsätze werden im AVA-Tool entsprechend der LV-Positionen angelegt und per Knopfdruck nach SAP übertragen. (ID 169)
  
  Im AVA-Tool werden aus den Stammsätzen für die jeweils vorzubereitende Ausschreibung (Jahresrahmenvertrag oder Einzelausschreibung) entsprechende "Muster-LV" angelegt und per Ausschreib-BANF (Banf 1) als Leistungsinhalt (nicht als Anlage!) an den Einkauf zur  weiteren Nutzung (bspw. Angebotseinholung) übergeben. 
  Der Einkauf nutzt dieses Muster-LV aus dem AVA-Tool um den/die Kontrakte im SAP anzulegen. 
  Die LV-Struktur des Dienstleisterportals entspricht der Struktur des Muster-LV aus dem AVA-Tool bzw. dem daraus angelegtem Kontrakt. 
  Muster-LV im AVA-Tool müssen je nach Status "eingefroren" werden, um diese revisionssicher zu archivieren. 
  Inhaltliche Änderungen des Muster-LV haben die Ablage als neue Version zur Folge.
- IREB:RequirementType: Funktion
- SpecIF:Priority: 1_hoch
- dcterms:modified: 2020-04-01T22:00:00.000Z

## REQ_AVA/Typicals_174 - 'Titel' (IREB:Requirement)
- dcterms:identifier: REQ_AVA/Typicals_174
- dcterms:subject: C6
- dcterms:description: wie 174
- IREB:RequirementType: Funktion
- SpecIF:Priority: 1_hoch
- dcterms:modified: 2020-04-01T22:00:00.000Z

## REQ_AVA/Typicals_175 - 'Titel' (IREB:Requirement)
- dcterms:identifier: REQ_AVA/Typicals_175
- dcterms:subject: C6
- dcterms:description: (Redaktionelle) Änderungen an den LV-Position (Leistungsstammsätzen) haben eine manuelle Anpassung der Muster-Leistungsverzeichnisse zur Folge.
  wie 174
- IREB:RequirementType: Funktion
- SpecIF:Priority: 1_hoch
- dcterms:modified: 2020-04-01T22:00:00.000Z

## REQ_AVA/Typicals_176 - 'Titel' (IREB:Requirement)
- dcterms:identifier: REQ_AVA/Typicals_176
- dcterms:subject: C6
- dcterms:description: wie 174
- IREB:RequirementType: Funktion
- SpecIF:Priority: 1_hoch
- dcterms:modified: 2020-04-01T22:00:00.000Z

## REQ_AVA/Typicals_177 - 'Titel' (IREB:Requirement)
- dcterms:identifier: REQ_AVA/Typicals_177
- dcterms:subject: C6
- dcterms:description: entfällt - siehe ID 67d
- IREB:RequirementType: Funktion
- SpecIF:Priority: 1_hoch
- dcterms:modified: 2020-04-01T22:00:00.000Z

## REQ_AVA/Typicals_178 - 'Titel' (IREB:Requirement)
- dcterms:identifier: REQ_AVA/Typicals_178
- dcterms:subject: C3
- dcterms:description: entfällt - siehe ID 67b
- IREB:RequirementType: Funktion
- SpecIF:Priority: 1_hoch
- dcterms:modified: 2020-04-01T22:00:00.000Z

## REQ_AVA/Typicals_179 - 'Titel' (IREB:Requirement)
- dcterms:identifier: REQ_AVA/Typicals_179
- dcterms:subject: C8
- dcterms:description: TB's sollen automatisch mit den Positionen im LV verknüpft und zur Ausschreibung ergänzt werden. Es sollen nur die TB's zu den im LV aufgeführten LV-Positionen automatisch (z. B. aus RUDI) rausgesucht und der Ausschreibung beigefügt werden. Es soll sichergestellt werden, dass alle notwendigen TB's übergeben werden und gleichzeitig TB's, welche in dem LV keine Berücksichtigung finden, nicht herausgegeben werden.
- IREB:RequirementType: Funktion
- SpecIF:Priority: 1_hoch
- dcterms:modified: 2020-04-01T22:00:00.000Z

## REQ_AVA/Typicals_18 - 'Titel' (IREB:Requirement)
- dcterms:identifier: REQ_AVA/Typicals_18
- dcterms:subject: C5
- dcterms:description: Die Angebotsstruktur (u. a. Loszusammensetzung) kann frei festgelegt werden.
- IREB:RequirementType: Funktion
- SpecIF:Priority: 1_hoch
- dcterms:modified: 2020-04-01T22:00:00.000Z

## REQ_AVA/Typicals_180 - 'Titel' (IREB:Requirement)
- dcterms:identifier: REQ_AVA/Typicals_180
- dcterms:subject: C3
- dcterms:description: Je Betriebsmittelpaket muss eine Einteilung in Invest und Aufwand möglich sein. Bei der Auswertung müssen Projektkosten nach Invest und Aufwand gegliedert werden. Lösung direkt über PSP-Elemente möglich.
- IREB:RequirementType: Funktion
- SpecIF:Priority: 1_hoch
- dcterms:modified: 2020-04-01T22:00:00.000Z

## REQ_AVA/Typicals_181 - 'Titel' (IREB:Requirement)
- dcterms:identifier: REQ_AVA/Typicals_181
- dcterms:subject: C9
- dcterms:description: Rahmenverträge müssen im AVA automatisiert über eine Schnittstelle durch SNB Mitarbeiter einspielbar sein
- IREB:RequirementType: Funktion
- SpecIF:Priority: 1_hoch
- dcterms:modified: 2020-04-01T22:00:00.000Z

## REQ_AVA/Typicals_182 - 'Titel' (IREB:Requirement)
- dcterms:identifier: REQ_AVA/Typicals_182
- dcterms:subject: C11
- dcterms:description: Bereits ausgelöste Abrufe dürfen nicht mehr geändert werden, nur ergänzt (Nachtrag)
- IREB:RequirementType: Funktion
- SpecIF:Priority: 1_hoch
- dcterms:modified: 2020-04-01T22:00:00.000Z

## REQ_AVA/Typicals_183 - 'Titel' (IREB:Requirement)
- dcterms:identifier: REQ_AVA/Typicals_183
- dcterms:subject: C12
- dcterms:description: Die LV-Positionen müssen in den Losen sowie von der Summe her auch in den Zahlungsschritten dargestellt werden. Die Aufteilung der Summe auf die Zahlungsschritte erfolgt über eine prozentuale Zuweisung und nicht über €-Beträge.
  Phase: Projektrealisierung -> erleichtert Q-Prognosen 
  (Überschneidung zu div. weiteren Cluster ggf. Darstellung über SNAP)
- IREB:RequirementType: Funktion
- SpecIF:Priority: 1_hoch
- dcterms:modified: 2020-04-01T22:00:00.000Z

## REQ_AVA/Typicals_184 - 'Titel' (IREB:Requirement)
- dcterms:identifier: REQ_AVA/Typicals_184
- dcterms:subject: C12
- dcterms:description: (3.7)
  Die Abrechnung in der MS/NS soll über das Dienstleisterportal (DL-Portal) direkt im SAP erfolgen. Das DL-Portal ist eine webbasierte Anwendung mit direkter Schnittstelle zum SAP zur Beauftragung der zu erbringenden Leistungen an und  Erfassung der tatsächlich erbrachten Leistungen gemäß des LV durch die Vertragsfirmen.
- IREB:RequirementType: Funktion
- SpecIF:Priority: 1_hoch
- dcterms:modified: 2020-04-01T22:00:00.000Z

## REQ_AVA/Typicals_185 - 'Titel' (IREB:Requirement)
- dcterms:identifier: REQ_AVA/Typicals_185
- dcterms:subject: C17
- dcterms:description: DL liefert IST-Leistungen zurück
- IREB:RequirementType: Funktion
- SpecIF:Priority: 1_hoch
- dcterms:modified: 2020-04-01T22:00:00.000Z

## REQ_AVA/Typicals_186 - 'Titel' (IREB:Requirement)
- dcterms:identifier: REQ_AVA/Typicals_186
- dcterms:subject: C17
- dcterms:description: Abnahme durchführen und für Zahlungsfreigabe dokumentieren
- IREB:RequirementType: Funktion
- SpecIF:Priority: 1_hoch
- dcterms:modified: 2020-04-01T22:00:00.000Z

## REQ_AVA/Typicals_187 - 'Titel' (IREB:Requirement)
- dcterms:identifier: REQ_AVA/Typicals_187
- dcterms:subject: C17
- dcterms:description: Rechnungsprüfung über die eingegebenen Aufmaße
- IREB:RequirementType: Funktion
- SpecIF:Priority: 1_hoch
- dcterms:modified: 2020-04-01T22:00:00.000Z

## REQ_AVA/Typicals_188 - 'Titel' (IREB:Requirement)
- dcterms:identifier: REQ_AVA/Typicals_188
- dcterms:subject: C19
- dcterms:description: automatisierte Übernahme von im Werkzeug durchgeführten "Nachkalkulationen" (nach Vergabe, Projektabschluss...) für die Kostenschätzung von neuen Projekten, einschließlich der Möglichkeit der Anpassung der Kostenverteilung (zwischen Betriebsmittelgruppen und Betriebsmittelpaketen)
- IREB:RequirementType: Funktion
- SpecIF:Priority: 1_hoch
- dcterms:modified: 2020-04-01T22:00:00.000Z

## REQ_AVA/Typicals_189 - 'Titel' (IREB:Requirement)
- dcterms:identifier: REQ_AVA/Typicals_189
- dcterms:subject: C20
- dcterms:description: Auswertung der Projekte/Bauvorhaben nach festgelegten und frei wählbaren Kriterien (z. B. Abweichungsanalyse bezogen auf Projektphasen) ist möglich.
- IREB:RequirementType: Funktion
- SpecIF:Priority: 1_hoch
- dcterms:modified: 2020-04-01T22:00:00.000Z

## REQ_AVA/Typicals_190 - 'Titel' (IREB:Requirement)
- dcterms:identifier: REQ_AVA/Typicals_190
- dcterms:subject: C8
- dcterms:description: Angebotserstellung, Übermittlung und Rechnungsprüfung(Aufmaßprüfung) von Leistungen an Dritte außerhalb von SAP. Es erfolgt keine Buchung im Hause Vattenfall.
- IREB:RequirementType: Funktion
- SpecIF:Priority: 1_hoch
- dcterms:modified: 2020-04-01T22:00:00.000Z

## REQ_AVA/Typicals_191 - 'Titel' (IREB:Requirement)
- dcterms:identifier: REQ_AVA/Typicals_191
- dcterms:subject: C8
- dcterms:description: Erfassung, Sicherung und Auswertung von Angeboten sowie verhandelten Preisen im Preisspiegel. Der Preisspiegel muss konfigurierbar sein, individuelle Einstellung z. B. prozentuale Abweichung von Bestpreis zu max.preis in anderer Farbe darzustellen. 
  Darstellung von internen Kalkulationspreisen je Position im Preisspiegel ggü. den Angebotspreisen. Es müssen die Kosten je LV-Positionen, Gewerk, Gesamtprojekt (jeder Hierarchieebene) angezeigt werden. Es muss die Möglichkeit geben die Angebote aller Bieter gegenüberzustellen und je Gewerk auszudrucken. Diese werden zur Prüfung an die Teilprojektleiter verteilt.
  
  Ausdrucke müssen je Bieter generiert werden können. Preispositionen müssen im Rahmen der Verhandlung ausgedruckt werden können. (Druckvorlagen müssen hinterlegt sein)
  
  Auswertungen und Ausgabe in Microsoftprodukte (z.B. Excel) von z. B. Preisspiegeln 
  -> Rollenberechtigung einzelner Teilgewerke // Ergänzung zu Punkt 29
- IREB:RequirementType: Funktion
- SpecIF:Priority: 1_hoch
- dcterms:modified: 2020-04-01T22:00:00.000Z

## REQ_AVA/Typicals_192 - 'Titel' (IREB:Requirement)
- dcterms:identifier: REQ_AVA/Typicals_192
- dcterms:description: Es werden dem Bauleiter die vom DL gemeldeten und die beauftragten Leistungen gegenübergestellt, damit leichter geprüft werden kann, ob alle Leistungen erbracht wurden  ​
- IREB:RequirementType: Funktion
- SpecIF:Priority: 1_hoch
- dcterms:modified: 2020-04-13T22:00:00.000Z

## REQ_AVA/Typicals_193 - 'Titel' (IREB:Requirement)
- dcterms:identifier: REQ_AVA/Typicals_193
- dcterms:description: Als Bauleiter: Es muss ein durchgängiger digitaler Abrechnungsprozess eingeführt werden.
- IREB:RequirementType: Funktion
- SpecIF:Priority: 1_hoch
- dcterms:modified: 2020-04-13T22:00:00.000Z

## REQ_AVA/Typicals_194 - 'Titel' (IREB:Requirement)
- dcterms:identifier: REQ_AVA/Typicals_194
- dcterms:description: Als Bauleiter muss ich Reportings erstellen können.​
- IREB:RequirementType: Funktion
- SpecIF:Priority: 1_hoch
- dcterms:modified: 2020-04-13T22:00:00.000Z

## REQ_AVA/Typicals_195 - 'Titel' (IREB:Requirement)
- dcterms:identifier: REQ_AVA/Typicals_195
- dcterms:description: Als Bauleiter: Es muss möglich sein, Kommentare an korrigierte Aufmaße zu setzen, damit der AN die Korrekturen erkennt.​​
- IREB:RequirementType: Funktion
- SpecIF:Priority: 1_hoch
- dcterms:modified: 2020-04-13T22:00:00.000Z

## REQ_AVA/Typicals_196 - 'Titel' (IREB:Requirement)
- dcterms:identifier: REQ_AVA/Typicals_196
- dcterms:description: Bestellte und nicht benötigte LV- Positionen müssen einfach ausgeblendet werden könne.
- IREB:RequirementType: Funktion
- SpecIF:Priority: 1_hoch
- dcterms:modified: 2020-04-13T22:00:00.000Z

## REQ_AVA/Typicals_197 - 'Titel' (IREB:Requirement)
- dcterms:identifier: REQ_AVA/Typicals_197
- dcterms:description: Eine Überführung der abgerechneten Positionen in die Typical-Learnings muss realisiert werden. Zudem müssen diese Learnings auch in den Leistungsverzeichnissen (im AVA) bereitgestellt werden. Dies muss für alle (Bau)leistungen im Rahmen SNAP umgesetzt werden
- IREB:RequirementType: Funktion
- SpecIF:Priority: 1_hoch
- dcterms:modified: 2020-04-13T22:00:00.000Z
- dcterms:creator: Herr Thomas Kiwus

## REQ_AVA/Typicals_20 - 'Titel' (IREB:Requirement)
- dcterms:identifier: REQ_AVA/Typicals_20
- dcterms:subject: C3
- dcterms:description: Ermittlung der “Operativen Kosten“ aus den “Direkten Kosten“ über eine dreistufige Zuschlagskalkulation (unterschiedliche prozentuale Aufschläge für Umlagen und Zuschläge je MuF, EGL und IDL)
- IREB:RequirementType: Funktion
- SpecIF:Priority: 1_hoch
- dcterms:modified: 2020-04-01T22:00:00.000Z

## REQ_AVA/Typicals_21 - 'Titel' (IREB:Requirement)
- dcterms:identifier: REQ_AVA/Typicals_21
- dcterms:subject: C3
- dcterms:description: Die Möglichkeit der Erstellung von automatisierten Preisbildungsblättern (GAEB) zur Einholung von Angeboten ist vorhanden. Es können mehrere Lose angelegt und die LV-Positionen auf diese verteilt und über diese ausgeschrieben werden.
- IREB:RequirementType: Funktion
- SpecIF:Priority: 1_hoch
- dcterms:modified: 2020-04-01T22:00:00.000Z

## REQ_AVA/Typicals_22 - 'Titel' (IREB:Requirement)
- dcterms:identifier: REQ_AVA/Typicals_22
- dcterms:subject: C20
- dcterms:description: Im Rahmen eines Projektabschlusses (Nachkalkulation) gibt es eine Möglichkeit zu ausführlichen Auswertungen und Vergleich zwischen geschätzten und eingetretenen Projektkosten, welche die einzelnen Phasen des Projektes sowie die abgerechneten Kosten gegenüberstellt
- IREB:RequirementType: Funktion
- SpecIF:Priority: 1_hoch
- dcterms:modified: 2020-04-01T22:00:00.000Z

## REQ_AVA/Typicals_25 - 'Titel' (IREB:Requirement)
- dcterms:identifier: REQ_AVA/Typicals_25
- dcterms:subject: C20
- dcterms:description: Auswertung der gesamten Projektkosten soll möglich sein (nicht nur der kalkulierten Gewerke und BMG, sondern aller im SAP zum Projekt vorhandenen Leistungen). Entfällt wenn alle Bereiche das gleiche System nutzen
- IREB:RequirementType: Funktion
- SpecIF:Priority: 1_hoch
- dcterms:modified: 2020-04-01T22:00:00.000Z

## REQ_AVA/Typicals_26 - 'Titel' (IREB:Requirement)
- dcterms:identifier: REQ_AVA/Typicals_26
- dcterms:subject: C20
- dcterms:description: Bei Projektänderungen während der Laufzeit, müssen Kalkulationen, Kostenverteilungen, LV-Erstellung nachträglich möglich sein. Dabei dürfen festgeschriebene Projektstände nicht überschrieben werden. Für den späteren Soll/IIST Abgleich von Projekten, müssen die nachträglichen Projektänderungen gekennzeichnet werden können.
- IREB:RequirementType: Funktion
- SpecIF:Priority: 1_hoch
- dcterms:modified: 2020-04-01T22:00:00.000Z

## REQ_AVA/Typicals_29 - 'Titel' (IREB:Requirement)
- dcterms:identifier: REQ_AVA/Typicals_29
- dcterms:subject: C6
- dcterms:description: Angebotskalkulation ggü. Dritte müssen flexibel gestaltet werden können (Internen Zuschlag in %)
- IREB:RequirementType: Funktion
- SpecIF:Priority: 1_hoch
- dcterms:modified: 2020-04-01T22:00:00.000Z

## REQ_AVA/Typicals_35 - 'Titel' (IREB:Requirement)
- dcterms:identifier: REQ_AVA/Typicals_35
- dcterms:subject: C3
- dcterms:description: Verschiedene Qualitätsstufen der Kostenermittlung in Anlehnung an DIN 276 müssen mit dem AVA-Programm/Leistungsplanungstool abgebildet werden können:
  - Projektphase Initialisierung: Kostenrahmen (Verantwortung: AM)
  - Projektphase Konzeption: Kostenschätzung 			(V: AM)
  - Projektphase Grobplanung: Kostenberechnung 		(V: AS)
  - Projektphase Feinplanung: Kostenanschlag 		(V: AS)
  - Projektphase Ausführung: Kostenprognose 			(V: AS)
  - Projektphase Review: Kostenfeststellung 		(V: AS/AM)
- IREB:RequirementType: Funktion
- SpecIF:Priority: 1_hoch
- dcterms:modified: 2020-04-01T22:00:00.000Z

## REQ_AVA/Typicals_36 - 'Titel' (IREB:Requirement)
- dcterms:identifier: REQ_AVA/Typicals_36
- dcterms:subject: C9
- dcterms:description: Fachliche technische Bewertung eingegangen Angeboten an Einkauf übergeben (z.B. FAQ) (Rollen + Berechtigungen!!) -> nice to have
- IREB:RequirementType: Funktion
- SpecIF:Priority: 1_hoch
- dcterms:modified: 2020-04-01T22:00:00.000Z

## REQ_AVA/Typicals_37 - 'Titel' (IREB:Requirement)
- dcterms:identifier: REQ_AVA/Typicals_37
- dcterms:subject: C5
- dcterms:description: Mengen / Kosten müssen auf verschiedenen Kostenträgern und -arten verteilt werden können (Multikontierung).
- IREB:RequirementType: Funktion
- SpecIF:Priority: 1_hoch
- dcterms:modified: 2020-04-01T22:00:00.000Z

## REQ_AVA/Typicals_4 - 'Titel' (IREB:Requirement)
- dcterms:identifier: REQ_AVA/Typicals_4
- dcterms:subject: C3
- dcterms:description: Bei Abweichungen, Nachträgen, Optionen soll die Möglichkeit bestehen diese in einem Feld zu kommentieren und im Nachhinein in den Projekten einzusehen.
- IREB:RequirementType: Funktion
- SpecIF:Priority: 1_hoch
- dcterms:modified: 2020-04-01T22:00:00.000Z

## REQ_AVA/Typicals_42 - 'Titel' (IREB:Requirement)
- dcterms:identifier: REQ_AVA/Typicals_42
- dcterms:subject: C2
- dcterms:description: Anlegen der Projektstruktur (Jahres-/Monatsscheiben, Kostenträger und Kostenart) durch zentral hinterlegte Vorgaben (Modellkalkulation). Dies beinhaltet das Anlegen der Kostenträgerstruktur mit dem SAP-TOP-Projekt
- IREB:RequirementType: Funktion
- SpecIF:Priority: 1_hoch
- dcterms:modified: 2020-04-01T22:00:00.000Z

## REQ_AVA/Typicals_43 - 'Titel' (IREB:Requirement)
- dcterms:identifier: REQ_AVA/Typicals_43
- dcterms:subject: C3
- dcterms:description: Leistungs-/Mengen und (Direkte-)Kostenermittlungen basieren auf verschiedenen Stamm-LVs
  - Externe Material- und Fremdleistungen (MuF)
  - Interne Materialbeistellungen
  - Interne Leistungskatalogen (Eigen- und Ingenieurdienstleistungen EGL/IDL)
- IREB:RequirementType: Funktion
- SpecIF:Priority: 1_hoch
- dcterms:modified: 2020-04-01T22:00:00.000Z

## REQ_AVA/Typicals_44 - 'Titel' (IREB:Requirement)
- dcterms:identifier: REQ_AVA/Typicals_44
- dcterms:subject: C3
- dcterms:description: Mengen / Kosten müssen auf verschiedene Monate/Jahre verteilt werden („Monats-/ Jahresscheiben“). Akt. GJ +  Folge-GJ in Monatsscheiben, danach Jahresscheiben
- IREB:RequirementType: Funktion
- SpecIF:Priority: 1_hoch
- dcterms:modified: 2020-04-01T22:00:00.000Z

## REQ_AVA/Typicals_45 - 'Titel' (IREB:Requirement)
- dcterms:identifier: REQ_AVA/Typicals_45
- dcterms:subject: C5
- dcterms:description: Projektbezogene Erlöse, Rückstellungen und Zahlpläne (Anzahlung, Teilzahlungen, etc.) müssen plan- und prognostizierbar sein
- IREB:RequirementType: Funktion
- SpecIF:Priority: 1_hoch
- dcterms:modified: 2020-04-01T22:00:00.000Z

## REQ_AVA/Typicals_46 - 'Titel' (IREB:Requirement)
- dcterms:identifier: REQ_AVA/Typicals_46
- dcterms:subject: C3
- dcterms:description: Import/Export von externen Planungsquellen (z.B. CSV, XML, IFC (Autodesk REVIT) o.ä.) um einen grafischen Bezug herzustellen.
- IREB:RequirementType: Funktion
- SpecIF:Priority: 1_hoch
- dcterms:modified: 2020-04-01T22:00:00.000Z

## REQ_AVA/Typicals_47 - 'Titel' (IREB:Requirement)
- dcterms:identifier: REQ_AVA/Typicals_47
- dcterms:subject: C3
- dcterms:description: Im AVA-Tool erfolgt eine Auswertung zur Mengenermittlung für die Ausschreibung von Jahresrahmenverträgen auf Grundlage der vergangenen  Jahre. Hierzu muss die Auswahl einzelner oder mehrerer Firmen/Kontrakte möglich sein. Die Auswertung erfolgt detailliert bis auf Positionsebene.
  Es werden zur Mengenermittlung die geplanten bzw. bestellten Positions-Mengen sowie die abgerechneten Positions-Mengen ausgewertet.
  Die Auswertung kann zur weiteren Bearbeitung nach bspw. MS Excel exportiert werden.
- IREB:RequirementType: Funktion
- SpecIF:Priority: 1_hoch
- dcterms:modified: 2020-04-01T22:00:00.000Z

## REQ_AVA/Typicals_49 - 'Titel' (IREB:Requirement)
- dcterms:identifier: REQ_AVA/Typicals_49
- dcterms:subject: C5
- dcterms:description: Kalkulation:
  Kostentrennung nach Betriebsmittelgruppen im Rahmen der Modellkalkulation muss möglich sein.
- IREB:RequirementType: Funktion
- SpecIF:Priority: 1_hoch
- dcterms:modified: 2020-04-01T22:00:00.000Z

## REQ_AVA/Typicals_5 - 'Titel' (IREB:Requirement)
- dcterms:identifier: REQ_AVA/Typicals_5
- dcterms:subject: C21
- dcterms:description: schneller Einsprung in die Projekteinzeldaten der für die Kostenschätzung zugrundeliegenden Projekte
- IREB:RequirementType: Funktion
- SpecIF:Priority: 1_hoch
- dcterms:modified: 2020-04-01T22:00:00.000Z

## REQ_AVA/Typicals_54 - 'Titel' (IREB:Requirement)
- dcterms:identifier: REQ_AVA/Typicals_54
- dcterms:subject: C6
- dcterms:description: Es muss ein zusätzliches Bemerkungsfeld für die nachträgliche Kommentierung von Standardpositionsbeschreibungen sowie Dummypositionen vorhanden sein (Kurz-/ Langtext)
- IREB:RequirementType: Funktion
- SpecIF:Priority: 1_hoch
- dcterms:modified: 2020-04-01T22:00:00.000Z

## REQ_AVA/Typicals_56 - 'Titel' (IREB:Requirement)
- dcterms:identifier: REQ_AVA/Typicals_56
- dcterms:subject: C6
- dcterms:description: siehe Punkt 56
- IREB:RequirementType: Funktion
- SpecIF:Priority: 1_hoch
- dcterms:modified: 2020-04-01T22:00:00.000Z

## REQ_AVA/Typicals_57 - 'Titel' (IREB:Requirement)
- dcterms:identifier: REQ_AVA/Typicals_57
- dcterms:subject: C6
- dcterms:description: Das kalkulierte Ausschreibungs-LV muss nach Übergabe, gemäß Markt-/ Bietersituation anpassbar sein. Bspw. Einzelne Positionen in Titel zusammenfassen, Zu- und Abschlagsfähig (Prozentual) oder pauschalisiert.
- IREB:RequirementType: Funktion
- SpecIF:Priority: 1_hoch
- dcterms:modified: 2020-04-01T22:00:00.000Z

## REQ_AVA/Typicals_58 - 'Titel' (IREB:Requirement)
- dcterms:identifier: REQ_AVA/Typicals_58
- dcterms:subject: C19
- dcterms:description: Abrechnung über GAEB
- IREB:RequirementType: Funktion
- SpecIF:Priority: 1_hoch
- dcterms:modified: 2020-04-01T22:00:00.000Z

## REQ_AVA/Typicals_59 - 'Titel' (IREB:Requirement)
- dcterms:identifier: REQ_AVA/Typicals_59
- dcterms:subject: C2
- dcterms:description: Es möglich sein, das AVA-Tool ohne einen SAP NeMo Bezug zu öffnen. Das direkte Öffnen des AVA-Tool dient der projektunabhängigen Bearbeitung von Bauvorhaben.
- IREB:RequirementType: Funktion
- SpecIF:Priority: 1_hoch
- dcterms:modified: 2020-04-01T22:00:00.000Z

## REQ_AVA/Typicals_60.9 - 'Titel' (IREB:Requirement)
- dcterms:identifier: REQ_AVA/Typicals_60.9
- dcterms:subject: C12
- dcterms:description: Abruf zum Dienstleistungskontrakt (3.6.3)
- IREB:RequirementType: Funktion
- SpecIF:Priority: 1_hoch
- dcterms:modified: 2020-04-01T22:00:00.000Z

## REQ_AVA/Typicals_62 - 'Titel' (IREB:Requirement)
- dcterms:identifier: REQ_AVA/Typicals_62
- dcterms:subject: C2
- dcterms:description: Bauvorhabenergänzung 
  - Bauabschnitte müssen im AVA-Tool angelegt, geändert/unterteilt oder gelöscht werden können. 
  - Bauabschnitte müssen für die schnellere Bearbeitung kopiert werden können.
- IREB:RequirementType: Funktion
- SpecIF:Priority: 1_hoch
- dcterms:modified: 2020-04-01T22:00:00.000Z

## REQ_AVA/Typicals_66 - 'Titel' (IREB:Requirement)
- dcterms:identifier: REQ_AVA/Typicals_66
- dcterms:subject: C2
- dcterms:description: Anlegen des Bauvorhabens im AVA-Tool:
  Das Bauvorhaben muss manuell und ohne einen SAP-Bezug  angelegt werden können. (reine Angebotskalkulation - für Anfragen von Extern)
- IREB:RequirementType: Funktion
- SpecIF:Priority: 1_hoch
- dcterms:modified: 2020-04-01T22:00:00.000Z

## REQ_AVA/Typicals_67 - 'Titel' (IREB:Requirement)
- dcterms:identifier: REQ_AVA/Typicals_67
- dcterms:subject: C10
- dcterms:description: Verhandelte Leistungsverzeichnisse (gemäß dem vorgegebenen Format) müssen wieder in das System 1 zu 1 überführt werden.
- IREB:RequirementType: Funktion
- SpecIF:Priority: 1_hoch
- dcterms:modified: 2020-04-01T22:00:00.000Z

## REQ_AVA/Typicals_69 - 'Titel' (IREB:Requirement)
- dcterms:identifier: REQ_AVA/Typicals_69
- dcterms:subject: C5
- dcterms:description: Zuordnung einzelner oder mehrerer CS-Aufträge (SAP-Aufträge)
- IREB:RequirementType: Funktion
- SpecIF:Priority: 1_hoch
- dcterms:modified: 2020-04-01T22:00:00.000Z

## REQ_AVA/Typicals_7 - 'Titel' (IREB:Requirement)
- dcterms:identifier: REQ_AVA/Typicals_7
- dcterms:subject: C3
- dcterms:description: EGL und IDL werden in Stunden erfasst und anhand der hinterlegten (anpassbaren) Stundensätzen in Euro umgerechnet.
- IREB:RequirementType: Funktion
- SpecIF:Priority: 1_hoch
- dcterms:modified: 2020-04-01T22:00:00.000Z

## REQ_AVA/Typicals_76 - 'Titel' (IREB:Requirement)
- dcterms:identifier: REQ_AVA/Typicals_76
- dcterms:subject: C5
- dcterms:description: Wird ein einzelner CS-Auftrag einem einzelnen Abschnitt (Ebene3) zugeordnet, ist dieser automatisch mit 100 % zu belegen.
- IREB:RequirementType: Funktion
- SpecIF:Priority: 1_hoch
- dcterms:modified: 2020-04-01T22:00:00.000Z

## REQ_AVA/Typicals_76.1 - 'Titel' (IREB:Requirement)
- dcterms:identifier: REQ_AVA/Typicals_76.1
- dcterms:subject: C5
- dcterms:description: In einem Abschnitt (Ebene3) können beliebig viele CS-Aufträge enthalten sein und zwischen den CS-Aufträgen muss die prozentuale Aufteilung möglich sein und die prozentuale Summe muss immer 100 % ergeben.
- IREB:RequirementType: Funktion
- SpecIF:Priority: 1_hoch
- dcterms:modified: 2020-04-01T22:00:00.000Z

## REQ_AVA/Typicals_76.2 - 'Titel' (IREB:Requirement)
- dcterms:identifier: REQ_AVA/Typicals_76.2
- dcterms:subject: C5
- dcterms:description: Ergibt die prozentuale Summe nicht 100 %, ist eine entsprechende Fehlermeldung anzuzeigen und eine Korrektur der Aufteilung wird notwendig und muss möglich sein.
- IREB:RequirementType: Funktion
- SpecIF:Priority: 1_hoch
- dcterms:modified: 2020-04-01T22:00:00.000Z

## REQ_AVA/Typicals_76.3 - 'Titel' (IREB:Requirement)
- dcterms:identifier: REQ_AVA/Typicals_76.3
- dcterms:subject: C5
- dcterms:description: Erweiterung einer Kalkulation um einen oder mehrerer SAP-Aufträge (3.3.11.4)
  - Werden in der Kalkulationsphase ein oder mehrere CS-Aufträge dem Abschnitt zugeordnet und die prozentuale Kostenverteilung nicht angepasst, ist eine entsprechende Fehlermeldung anzuzeigen und eine Korrektur der Aufteilung notwendig und möglich.
- IREB:RequirementType: Funktion
- SpecIF:Priority: 1_hoch
- dcterms:modified: 2020-04-01T22:00:00.000Z

## REQ_AVA/Typicals_77 - 'Titel' (IREB:Requirement)
- dcterms:identifier: REQ_AVA/Typicals_77
- dcterms:subject: C5
- dcterms:description: entfällt - siehe ID 69
- IREB:RequirementType: Funktion
- SpecIF:Priority: 1_hoch
- dcterms:modified: 2020-04-01T22:00:00.000Z

## REQ_AVA/Typicals_78 - 'Titel' (IREB:Requirement)
- dcterms:identifier: REQ_AVA/Typicals_78
- dcterms:subject: C2
- dcterms:description: Während der Projektphase Beantragung kann es im Rahmen der Projektportfolio-Betrachtung zu Anpassungen im Projektablauf einzelner Projekte kommen. Der Rücksprung muss im System gewährleistet sein. Diese Anpassungsabstimmungen wiederholen sich ebenfalls in späteren Projektphasen in Abstimmung zwischen AM und AS.
- IREB:RequirementType: Funktion
- SpecIF:Priority: 1_hoch
- dcterms:modified: 2020-04-01T22:00:00.000Z

## REQ_AVA/Typicals_80 - 'Titel' (IREB:Requirement)
- dcterms:identifier: REQ_AVA/Typicals_80
- dcterms:subject: C5
- dcterms:description: Nach der Ermittlung der Kosten im AVA-Tool werden die Schätzkosten übernommen und im SAP NeMo dargestellt.
- IREB:RequirementType: Funktion
- SpecIF:Priority: 1_hoch
- dcterms:modified: 2020-04-01T22:00:00.000Z

## REQ_AVA/Typicals_81 - 'Titel' (IREB:Requirement)
- dcterms:identifier: REQ_AVA/Typicals_81
- dcterms:subject: C7.2
- dcterms:description: siehe Punkt 82.3 sowie 81
  
  Für Jahresrahmenverträge erfolgt keine Unterscheidung zwischen geplanten und ungeplanten Positionen. Die Mengen sind immer >0.
- IREB:RequirementType: Funktion
- SpecIF:Priority: 1_hoch
- dcterms:modified: 2020-04-01T22:00:00.000Z

## REQ_AVA/Typicals_82 - 'Titel' (IREB:Requirement)
- dcterms:identifier: REQ_AVA/Typicals_82
- dcterms:subject: C7.2
- dcterms:description: Ausschreib-BANF (BANF1) Einzelprojekte: (s. auch Nummer 81)
  Bei der Kalkulation der Mengen für die Erstellung der Ausschreib-Banf muss im AVA-Tool unterschieden werden können zwischen geplanten und ungeplanten Positionen. Diese müssen im Leistungsverzeichnis erkenntlich sein. Die Auswahl zwischen geplanten und ungeplanten Leistungen im Leistungsverzeichnis muss per Klick möglich sein.
- IREB:RequirementType: Funktion
- SpecIF:Priority: 1_hoch
- dcterms:modified: 2020-04-01T22:00:00.000Z

## REQ_AVA/Typicals_82.1 - 'Titel' (IREB:Requirement)
- dcterms:identifier: REQ_AVA/Typicals_82.1
- dcterms:subject: C3
- dcterms:description: Die ext. Ingenieurbüros sollen lesenden / schreibenden / löschenden Zugriff auf den ihr zugeordneten Bereich im AVA-Tool erhalten, alle anderen Bereiche sind für die ext. Ingenieurbüros zu sperren.
- IREB:RequirementType: Funktion
- SpecIF:Priority: 1_hoch
- dcterms:modified: 2020-04-01T22:00:00.000Z

## REQ_AVA/Typicals_82.2 - 'Titel' (IREB:Requirement)
- dcterms:identifier: REQ_AVA/Typicals_82.2
- dcterms:subject: C6
- dcterms:description: Bestellpakete mit Einkauf abstimmbar machen, Leistungspositionen werden Leistungsverzeichnissen zugewiesen
- IREB:RequirementType: Funktion
- SpecIF:Priority: 1_hoch
- dcterms:modified: 2020-04-01T22:00:00.000Z

## REQ_AVA/Typicals_83 - 'Titel' (IREB:Requirement)
- dcterms:identifier: REQ_AVA/Typicals_83
- dcterms:subject: C11
- dcterms:description: siehe Punkt 83
- IREB:RequirementType: Funktion
- SpecIF:Priority: 1_hoch
- dcterms:modified: 2020-04-01T22:00:00.000Z

## REQ_AVA/Typicals_84 - 'Titel' (IREB:Requirement)
- dcterms:identifier: REQ_AVA/Typicals_84
- dcterms:subject: C3
- dcterms:description: Die Freigabe zur Bearbeitung an die ext. Ingenieurbüros erfolgt auf der Projektebene (Ebene2) eines Netzbauprojektes im SAP NeMo.
- IREB:RequirementType: Funktion
- SpecIF:Priority: 1_hoch
- dcterms:modified: 2020-04-01T22:00:00.000Z

## REQ_AVA/Typicals_84.1 - 'Titel' (IREB:Requirement)
- dcterms:identifier: REQ_AVA/Typicals_84.1
- dcterms:subject: C3
- dcterms:description: Der SNB-Projektleiter muss nach der Übergabe der Kalkulation und Planungsunterlagen von dem ext. Ingenieurbüro an die Stromnetz Berlin die Möglichkeit haben, die Daten der ext. Ingenieurbüros "einzufrieren" bzw. gegen Änderungen zu sperren.
- IREB:RequirementType: Funktion
- SpecIF:Priority: 1_hoch
- dcterms:modified: 2020-04-01T22:00:00.000Z

## REQ_AVA/Typicals_84.2 - 'Titel' (IREB:Requirement)
- dcterms:identifier: REQ_AVA/Typicals_84.2
- dcterms:subject: C3
- dcterms:description: Die vorhandenen Vertragsfirmen stellen ein eigenes AVA-Tool zur Verfügung und die Daten werden mittels einer GAEB Daten ausgetauscht.
  (Vorzugsweise, zur Vermeidung von Formatierungsproblemen, wäre der Einsatz des gleichen AVA-Tools wie bei SNB sinnvoll.)
- IREB:RequirementType: Funktion
- SpecIF:Priority: 1_hoch
- dcterms:modified: 2020-04-01T22:00:00.000Z

## REQ_AVA/Typicals_84.3 - 'Titel' (IREB:Requirement)
- dcterms:identifier: REQ_AVA/Typicals_84.3
- dcterms:subject: C3
- dcterms:description: Die Die Kalkulation erfolgt anhand vorhandener Leistungsverzeichnisse der Jahresrahmenverträge der jeweiligen Gewerke.
  Das Leistungsverzeichnis/Kalkulationsmodell bezieht sich auf den 0 Preis +/- n %.
- IREB:RequirementType: Funktion
- SpecIF:Priority: 1_hoch
- dcterms:modified: 2020-04-01T22:00:00.000Z

## REQ_AVA/Typicals_84.4 - 'Titel' (IREB:Requirement)
- dcterms:identifier: REQ_AVA/Typicals_84.4
- dcterms:subject: C3
- dcterms:description: Nach Kalkulation durch ein ext. Ingenieurbüro, wird diese Kalkulation durch den Stromnetz Berlin- Mitarbeiter geprüft und für eine Ausschreibung (BANF1) oder Abrufbestellung (BANF2/Bestellung) weiter genutzt.
- IREB:RequirementType: Funktion
- SpecIF:Priority: 1_hoch
- dcterms:modified: 2020-04-01T22:00:00.000Z

## REQ_AVA/Typicals_84.5 - 'Titel' (IREB:Requirement)
- dcterms:identifier: REQ_AVA/Typicals_84.5
- dcterms:subject: C3
- dcterms:description: Bei der Fremdkalkulation darf ein beauftragtes ext. Ingenieurbüro nur ihre beauftragten Netzaufträge/Kalkulationen sehen. Netzaufträge/Kalkulationen die durch ein anderes ext. Ingenieurbüro ausgeführt werden, dürfen nicht sichtbar sein.
- IREB:RequirementType: Funktion
- SpecIF:Priority: 1_hoch
- dcterms:modified: 2020-04-01T22:00:00.000Z

## REQ_AVA/Typicals_84.6 - 'Titel' (IREB:Requirement)
- dcterms:identifier: REQ_AVA/Typicals_84.6
- dcterms:subject: C3
- dcterms:description: Ausschreibungs-LV erstellen:
  
  Die Erstellung der LV- Positionen kann je Gewerk durch den Projektverantwortlichen händisch eingetragen bzw. aus vorhandenen Stamm-LVs können Positionen herauskopiert werden.
- IREB:RequirementType: Funktion
- SpecIF:Priority: 1_hoch
- dcterms:modified: 2020-04-01T22:00:00.000Z

## REQ_AVA/Typicals_85 - 'Titel' (IREB:Requirement)
- dcterms:identifier: REQ_AVA/Typicals_85
- dcterms:subject: C5
- dcterms:description: Die internen und externen IDL (Ingenieurdienstleistungen intern) und EGL (Eigenleistungen intern) werden im AVA-Tool geplant und sind nach SAP NeMo zu übertragen.
- IREB:RequirementType: Funktion
- SpecIF:Priority: 1_hoch
- dcterms:modified: 2020-04-01T22:00:00.000Z

## REQ_AVA/Typicals_85.2 - 'Titel' (IREB:Requirement)
- dcterms:identifier: REQ_AVA/Typicals_85.2
- dcterms:subject: C5
- dcterms:description: Die Multikontierung dient der prozentualen Aufteilung von unterschiedlichen Leistungen zwischen verschiedenen SAP-Aufträgen (SAP-Aufträge).
  Die prozentuale Aufteilung zwischen den SAP-Aufträgen ist unabhängig von einer Kostenkalkulation, dem Ausschreibprozess oder einer Abrufbestellung zur Verfügung zu stellen.
  Die Summe der prozentualen Aufteilung muss immer 100 % ergeben.
- IREB:RequirementType: Funktion
- SpecIF:Priority: 1_hoch
- dcterms:modified: 2020-04-01T22:00:00.000Z

## REQ_AVA/Typicals_86 - 'Titel' (IREB:Requirement)
- dcterms:identifier: REQ_AVA/Typicals_86
- dcterms:subject: C20
- dcterms:description: Übersicht: Kostenberechnung - Auftrag - Nachtrag - Abrechnung für ein Projekt
- IREB:RequirementType: Funktion
- SpecIF:Priority: 1_hoch
- dcterms:modified: 2020-04-01T22:00:00.000Z

## REQ_AVA/Typicals_89 - 'Titel' (IREB:Requirement)
- dcterms:identifier: REQ_AVA/Typicals_89
- dcterms:subject: C3
- dcterms:description: Ableitung von Schätzkosten aus der digitalen Zeichnung
- IREB:RequirementType: Funktion
- SpecIF:Priority: 1_hoch
- dcterms:modified: 2020-04-01T22:00:00.000Z

## REQ_AVA/Typicals_90 - 'Titel' (IREB:Requirement)
- dcterms:identifier: REQ_AVA/Typicals_90
- dcterms:subject: C7.3
- dcterms:description: Für den Einkaufsprozess muss es die Möglichkeit der Ausgabe der Leistungsverzeichnisse im Excel-Format (alle Formate) geben.
- IREB:RequirementType: Funktion
- SpecIF:Priority: 1_hoch
- dcterms:modified: 2020-04-01T22:00:00.000Z

## REQ_AVA/Typicals_91 - 'Titel' (IREB:Requirement)
- dcterms:identifier: REQ_AVA/Typicals_91
- dcterms:subject: C7.1
- dcterms:description: siehe 91
- IREB:RequirementType: Funktion
- SpecIF:Priority: 1_hoch
- dcterms:modified: 2020-04-01T22:00:00.000Z

## REQ_AVA/Typicals_92 - 'Titel' (IREB:Requirement)
- dcterms:identifier: REQ_AVA/Typicals_92
- dcterms:subject: C12
- dcterms:description: Abruf aus allen Rahmenverträgen aus einem System und dadurch optimierte Fremdkapazitätennutzung
- IREB:RequirementType: Funktion
- SpecIF:Priority: 1_hoch
- dcterms:modified: 2020-04-01T22:00:00.000Z

## REQ_AVA/Typicals_93 - 'Titel' (IREB:Requirement)
- dcterms:identifier: REQ_AVA/Typicals_93
- dcterms:subject: C8
- dcterms:description: Im Rahmen der Angebotsauswertung, muss es möglich sein vers. Angebotsversionen (z. B. überarbeitetes Angebot) eines Bieters/ der gleichen Leistungsposition zum Vergleich heranzuziehen. - Zudem muss die Möglichkeit bestehen einen Bieter (im Rahmen der Ausschreibung -> Verlauf der Verhandlung muss je Bieter dargestellt werden können) mehrfach in das System einzulesen.
- IREB:RequirementType: Funktion
- SpecIF:Priority: 1_hoch
- dcterms:modified: 2020-04-01T22:00:00.000Z

## REQ_AVA/Typicals_93.1 - 'Titel' (IREB:Requirement)
- dcterms:identifier: REQ_AVA/Typicals_93.1
- dcterms:subject: C10
- dcterms:description: Nach der Vergabe werden in dem SAP System ein oder mehrere Verträge mit den bepreisten Leistungspositionen angelegt. Diese Verträge müssen im AVA-Tool zur Kalkulation und Beauftragung mittels Abrufbestellungen zur Verfügung stehen. Die Daten müssen in Abhängigkeit, der Vergabe und den erstellten Rahmenverträge mittels einer automatisierten Schnittstelle aus dem SAP System ins AVA-Tool transportiert werden. Bei dem Transport müssen alle relevanten Informationen wie z.B. Kontaktnummer, Kreditornummer, Preispositionsnummer (intern, extern), Projektnummer, übertragen werden. Die Übergabe der Informationen muss mittels einer Schnittstelle automatisch stattfinden.
- IREB:RequirementType: Funktion
- SpecIF:Priority: 1_hoch
- dcterms:modified: 2020-04-01T22:00:00.000Z

## REQ_AVA/Typicals_93.3 - 'Titel' (IREB:Requirement)
- dcterms:identifier: REQ_AVA/Typicals_93.3
- dcterms:subject: C11
- dcterms:description: Rollenberechtigung
- IREB:RequirementType: Funktion
- SpecIF:Priority: 1_hoch
- dcterms:modified: 2020-04-01T22:00:00.000Z

## REQ_AVA/Typicals_94 - 'Titel' (IREB:Requirement)
- dcterms:identifier: REQ_AVA/Typicals_94
- dcterms:subject: C7.1
- dcterms:description: Ausschreib BANF Einzelprojekte (3.5.1)
  Die Ausschreib-BANF  für Einzelprojekte (kontiert / unkontiert) wird angelegt, nachdem eine Kalkulation auf Basis eines spez. (siehe Punkt xxx) kalkulierten Leistungsverzeichnisses im AVA-Tool erstellt wurde (s. ID 164 ).
  Nach Übergabe an die SAP Systeme wird nur die Ausschreib-Banf angelegt (kein direkter Abruf aus Verträgen möglich)
  Alle notwendigen Projektunterlagen für den Ausschreibungsprozess werden im AVA-Tool der spez. Maßnahme zugeordnet und automatisch an die Ausschreib-Banf als Anlage(n) angehangen.
  (s. auch IDs 156 + 157) ?
- IREB:RequirementType: Funktion
- SpecIF:Priority: 1_hoch
- dcterms:modified: 2020-04-01T22:00:00.000Z

## REQ_AVA/Typicals_95 - 'Titel' (IREB:Requirement)
- dcterms:identifier: REQ_AVA/Typicals_95
- dcterms:subject: C15
- dcterms:description: Die erbrachten Leistungen sind im Dienstleisterportal durch die Vertragsfirmen zu erfassen und werden als Leistungserfassungsblätter (LEB) zur Abnahme gespeichert.
- IREB:RequirementType: Funktion
- SpecIF:Priority: 1_hoch
- dcterms:modified: 2020-04-01T22:00:00.000Z

## REQ_AVA/Typicals_95.1 - 'Titel' (IREB:Requirement)
- dcterms:identifier: REQ_AVA/Typicals_95.1
- dcterms:subject: C15
- dcterms:description: Mit dem Speichern sind die LEB für die Vertragsfirmen gegen weitere Bearbeitung zu sperren und über Business Workplace im SAP zur weiteren Bearbeitung durch SNB zur Verfügung zu stellen.
- IREB:RequirementType: Funktion
- SpecIF:Priority: 1_hoch
- dcterms:modified: 2020-04-01T22:00:00.000Z

## REQ_AVA/Typicals_95.10 - 'Titel' (IREB:Requirement)
- dcterms:identifier: REQ_AVA/Typicals_95.10
- dcterms:subject: C15
- dcterms:description: Zugriff auf das AVA von externen Firmen zum Zweck der Aufmaßerstellung
- IREB:RequirementType: Funktion
- SpecIF:Priority: 1_hoch
- dcterms:modified: 2020-04-01T22:00:00.000Z

## REQ_AVA/Typicals_95.2 - 'Titel' (IREB:Requirement)
- dcterms:identifier: REQ_AVA/Typicals_95.2
- dcterms:subject: C15
- dcterms:description: Die Abnahme / Ablehnung der im LEB erfassten Leistungen hat in einem zweistufigen Verfahren (siehe Vier-Augenprinzip) zu erfolgen.
- IREB:RequirementType: Funktion
- SpecIF:Priority: 1_hoch
- dcterms:modified: 2020-04-01T22:00:00.000Z

## REQ_AVA/Typicals_95.3 - 'Titel' (IREB:Requirement)
- dcterms:identifier: REQ_AVA/Typicals_95.3
- dcterms:subject: C15
- dcterms:description: Ein LEB, in dem falsch erfasste Leistungen (falsche LV-Position, falsche Mengenangaben, nicht erbrachte LV-Position) enthält ist abzulehnen und im  SAP System für die SNB gegen eine weitere Bearbeitung zu sperren. Das LEB ist der Vertragsfirma zur Korrektur im DL-Portal zur Verfügung zu stellen.
  Nach der Korrektur des LEB durch die Vertragsfirma wird das LEB erneut zur Abnahme gespeichert (s. s. ID 95. u. 95.2).
- IREB:RequirementType: Funktion
- SpecIF:Priority: 1_hoch
- dcterms:modified: 2020-04-01T22:00:00.000Z

## REQ_AVA/Typicals_95.4 - 'Titel' (IREB:Requirement)
- dcterms:identifier: REQ_AVA/Typicals_95.4
- dcterms:subject: C15
- dcterms:description: Die Ablehnung des LEB durch SNB kann in der ersten oder zweiten Abnahmestufe des Business Workplace erfolgen.
- IREB:RequirementType: Funktion
- SpecIF:Priority: 1_hoch
- dcterms:modified: 2020-04-01T22:00:00.000Z

## REQ_AVA/Typicals_95.5 - 'Titel' (IREB:Requirement)
- dcterms:identifier: REQ_AVA/Typicals_95.5
- dcterms:subject: C15
- dcterms:description: Mit der zweiten Bestätigung im Business Workplace soll automatisch der Wareneingang im SAP gebucht werden und den Prozess der Rechnungslegung / Buchung starten.
- IREB:RequirementType: Funktion
- SpecIF:Priority: 1_hoch
- dcterms:modified: 2020-04-01T22:00:00.000Z

## REQ_AVA/Typicals_95.6 - 'Titel' (IREB:Requirement)
- dcterms:identifier: REQ_AVA/Typicals_95.6
- dcterms:subject: C15
- dcterms:description: Die Abrechnung an die Vertragsfirmen hat in der Mittel-/Niederspannung mittels dem Gutschriftenverfahren zu erfolgen.
- IREB:RequirementType: Funktion
- SpecIF:Priority: 1_hoch
- dcterms:modified: 2020-04-01T22:00:00.000Z

## REQ_AVA/Typicals_95.7 - 'Titel' (IREB:Requirement)
- dcterms:identifier: REQ_AVA/Typicals_95.7
- dcterms:subject: C15
- dcterms:description: Die abgenommenen LEB und nicht abgenommenen LEBs sind durch einen entsprechenden Status zu kennzeichnen.
- IREB:RequirementType: Funktion
- SpecIF:Priority: 1_hoch
- dcterms:modified: 2020-04-01T22:00:00.000Z

## REQ_AVA/Typicals_95.8 - 'Titel' (IREB:Requirement)
- dcterms:identifier: REQ_AVA/Typicals_95.8
- dcterms:subject: C15
- dcterms:description: Hat ein LEB durch die Abnahme in der zweiten Stufe den Status endabgenommen erhalten, darf kein weiteres LEB zu dem Abschnitt erfasst werden können.
- IREB:RequirementType: Funktion
- SpecIF:Priority: 1_hoch
- dcterms:modified: 2020-04-01T22:00:00.000Z

## REQ_AVA/Typicals_95.9 - 'Titel' (IREB:Requirement)
- dcterms:identifier: REQ_AVA/Typicals_95.9
- dcterms:subject: C15
- dcterms:description: Unabhängig von der Erfassung von geplanten (beauftragte) und ungeplanten (zusätzlich erforderliche) Leistungspositionen im LEB, sollen die LEB ins AVA-Tool automatisiert übernommen werden.
- IREB:RequirementType: Funktion
- SpecIF:Priority: 1_hoch
- dcterms:modified: 2020-04-01T22:00:00.000Z

## REQ_AVA/Typicals_97a - 'Titel' (IREB:Requirement)
- dcterms:identifier: REQ_AVA/Typicals_97a
- dcterms:subject: C15
- dcterms:description: Aufmaßprüfung mittels 4-Augen-Prinzip und anschließendem Festschreiben im AVA.
- IREB:RequirementType: Funktion
- SpecIF:Priority: 1_hoch
- dcterms:modified: 2020-04-01T22:00:00.000Z

## REQ_AVA/Typicals_98 - 'Titel' (IREB:Requirement)
- dcterms:identifier: REQ_AVA/Typicals_98
- dcterms:subject: C21
- dcterms:description: Gesamte Kostenschätzung, Ausschreibung, Vergabe und Abrechnung inkl. Nachträge in einem System zur SST-optimierung und Fehlervermeidung
- IREB:RequirementType: Funktion
- SpecIF:Priority: 1_hoch
- dcterms:modified: 2020-04-01T22:00:00.000Z

## Geschäftsprozesse (SpecIF:Heading)
- dcterms:type: SpecIF:BusinessProcesses

## Modellelemente (Glossar) (SpecIF:Heading)
- dcterms:type: SpecIF:Glossary

## Akteure (SpecIF:Heading)

## Zustände (SpecIF:Heading)

## Ereignisse (SpecIF:Heading)

## Kollektionen und Gruppen (SpecIF:Heading)

## Controlling (User-Stories) (SpecIF:Outline)

## Controlling (SpecIF:Heading)

## Beantragung - Projektkalkulation (Kalkulationsmodell) (SpecIF:UserStory)
- dcterms:identifier: UST_Controlling_0001
- dcterms:description: Kalkulationsbegleitend und final eine Übersicht aller Projekte (KTO´s) des Planungsportfolios in der Detailierung des Kalkulationsmodells (über die Laufzeit des Projektes) und über die Gesamtheit des Projektvolumens der nächsten 5 Jahre.
- dcterms:modified: 2020-05-18T22:00:00.000Z
- dcterms:creator: Dirk Baranowski

## Beantragung - Projektkalkulation (Kalkulationsmodell) (SpecIF:UserStory)
- dcterms:identifier: UST_Controlling_0002
- dcterms:description: Zuordnung / Aufteilung in Eigen- und Fremdleistung brauchen wir, um Ressourcenplanung plausibilisieren zu können.
- dcterms:modified: 2020-05-18T22:00:00.000Z
- dcterms:creator: Katarina Plamenac

## Beantragung - Projektkalkulation (Kalkulationsmodell) (SpecIF:UserStory)
- dcterms:identifier: UST_Controlling_0003
- dcterms:description: Die Projektkalkulation soll dem Kalkulationsmodell entsprechen.
- dcterms:modified: 2020-05-18T22:00:00.000Z
- dcterms:creator: Andreas Litwiakow

## Beantragung - Projektkalkulation (Kalkulationsmodell) (SpecIF:UserStory)
- dcterms:identifier: UST_Controlling_0004
- dcterms:description: wichtig ist die Analyse/Plausibilisierung von Zwischenständen der Planung nach Kalkulationsergebnissen und vor Finalisierung.
- dcterms:modified: 2020-05-18T22:00:00.000Z
- dcterms:creator: Katarina Plamenac

## Beantragung - Kaufmännische Einordnung (SpecIF:UserStory)
- dcterms:identifier: UST_Controlling_0005
- dcterms:description: Eine Unterteilung der InvestProjekte in Ersatz und Erweiterung für die Berechnung der ReInvestquote… (einjährig und vorausschauend)
- dcterms:modified: 2020-05-18T22:00:00.000Z
- dcterms:creator: Tamara Franke

## Beantragung - Kaufmännische Einordnung (SpecIF:UserStory)
- dcterms:identifier: UST_Controlling_0006
- dcterms:description: kfm. Einordnung der Entwicklung des Anlagenvermögens (Afa, Rückstellungen)
- dcterms:modified: 2020-05-18T22:00:00.000Z
- dcterms:creator: Tamara Franke

## Beantragung - Planzahlen / Kennzahlen verwenden (SpecIF:UserStory)
- dcterms:identifier: UST_Controlling_0007
- dcterms:description: Als Controller brauche ich eine einfache Möglichkeit des Abgleichs von bestehenden Daten aus der Planung zu anderen Projekt-Datenständen (Prognose, aktuelle „Überlegungen“), um Abweichungen erklären zu können und ggf. steuernd einzugreifen
- dcterms:modified: 2020-05-18T22:00:00.000Z
- dcterms:creator: Christian Colberg

## Beantragung - Planzahlen / Kennzahlen verwenden (SpecIF:UserStory)
- dcterms:identifier: UST_Controlling_0008
- dcterms:description: Bereitstellung von Kennzahlen für Analysen / Abgleich Targets (Planungsinput) <> Kalkulation u.a. Einsatz Eigenleistungen in Projekten <> PMVP; aktivierte EL, MuF Opex, Capex …
- dcterms:modified: 2020-05-18T22:00:00.000Z
- dcterms:creator: Dirk Baranowski

## Beantragung - Dokumentation Beantragung (SpecIF:UserStory)
- dcterms:identifier: UST_Controlling_0009
- dcterms:description: Inhalte der Projektrichtlinie zu Projektantrag eines Projektes sind berücksichtigt [Inhalte abgleichen mit Projektakte]
- dcterms:modified: 2020-05-18T22:00:00.000Z
- dcterms:creator: Roland Reball

## Beantragung - Dokumentation Beantragung (SpecIF:UserStory)
- dcterms:identifier: UST_Controlling_0010
- dcterms:description: Für die Planung benötigen wir eine Projektbeschreibung als Steckbrief und in Management Form
- dcterms:modified: 2020-05-18T22:00:00.000Z
- dcterms:creator: Andreas Litwiakow

## Beantragung - Dokumentation Beantragung (SpecIF:UserStory)
- dcterms:identifier: UST_Controlling_0011
- dcterms:description: V1: Projektbeantragung im ordentlichen Unternehmensplanungsprozess
  V2: außerordentliche/ außerplanmäßige Projektbeantragung mittels GF-Vorlage
- dcterms:modified: 2020-05-18T22:00:00.000Z
- dcterms:creator: Dirk Baranowski

## Beantragung - Dokumentation Beantragung (SpecIF:UserStory)
- dcterms:identifier: UST_Controlling_0012
- dcterms:description: es gibt Projektbeantragung im Planungsprozess und außerplanmäpßig. In beiden Fällen wird Projektantrag benötigt.
- dcterms:modified: 2020-05-18T22:00:00.000Z
- dcterms:creator: Katarina Plamenac

## Beantragung - Sonstige (SpecIF:UserStory)
- dcterms:identifier: UST_Controlling_0013
- dcterms:description: Der Portfolioprozess muss auf "Störgrößen" reagieren können!
- dcterms:modified: 2020-05-18T22:00:00.000Z
- dcterms:creator: Dirk Baranowski

## Beantragung - Sonstige (SpecIF:UserStory)
- dcterms:identifier: UST_Controlling_0014
- dcterms:description: Verknüpfungen von Projekten untereinander (bspw. bei Mat.verkauf und Schrotterlöse)
- dcterms:modified: 2020-05-18T22:00:00.000Z
- dcterms:creator: Tamara Franke

## Beantragung - Sonstige (SpecIF:UserStory)
- dcterms:identifier: UST_Controlling_0015
- dcterms:description: Übersicht der Investitionen (CAPEX) für die Erlösplanung/ Langfristplanung nach der Struktur Projektportfolio je Jahr u.a. Betriebsmittelgruppen, BNetzA-Anlagenklassen und bis 2050; Werte in HGB und IFRS
- dcterms:modified: 2020-05-18T22:00:00.000Z
- dcterms:creator: Dirk Baranowski

## Beantragung - Sonstige (SpecIF:UserStory)
- dcterms:identifier: UST_Controlling_0016
- dcterms:description: Die Projektplanung soll Geschäftsjahres, Betriebsmittel  genau, Kostenarten scharf im kfm. System abgebildet sein.
- dcterms:modified: 2020-05-18T22:00:00.000Z
- dcterms:creator: Andreas Litwiakow

## Beantragung - Sonstige (SpecIF:UserStory)
- dcterms:identifier: UST_Controlling_0017
- dcterms:description: Projektzuordnung in Bereiche soll möglich sein, HS, MS/NS, Metering z.B. via Projektkategorien / Projekttypen
- dcterms:modified: 2020-05-18T22:00:00.000Z
- dcterms:creator: Andreas Litwiakow

## Beantragung - Sonstige (SpecIF:UserStory)
- dcterms:identifier: UST_Controlling_0018
- dcterms:description: „kein Budget ohne SAP“ Eindeutige Budgetallokation als Dokumentation bereits bei Beginn eines Projektes
- dcterms:modified: 2020-05-18T22:00:00.000Z
- dcterms:creator: Katarina Plamenac

## Realisierung - Prognose (SpecIF:UserStory)
- dcterms:identifier: UST_Controlling_0019
- dcterms:description: Plausible Prognose Jahres-Scheiben:
  - Einzelnes Projekt (Prognose vs. Verfügt/ Zuschläge)
  - Projektportfolio: Steuerung auf Zielwerte z.B. OPEX, CAPEX: siehe oben, Aggregation der einzelnen Projekte, plausible Größenordnung Überbeauftragung
- dcterms:modified: 2020-05-18T22:00:00.000Z
- dcterms:creator: André Minke

## Realisierung - Prognose (SpecIF:UserStory)
- dcterms:identifier: UST_Controlling_0020
- dcterms:description: Projektprognose im Zusammenhang mit anderen betr. Prozessen (bspw. Obligo, Projektschließung)
- dcterms:modified: 2020-05-18T22:00:00.000Z
- dcterms:creator: Tamara Franke

## Realisierung - Prognose (SpecIF:UserStory)
- dcterms:identifier: UST_Controlling_0021
- dcterms:description: Budget >= Prognose sonst Nachtrag
- dcterms:modified: 2020-05-18T22:00:00.000Z
- dcterms:creator: Dirk Baranowski

## Realisierung - Prognose (SpecIF:UserStory)
- dcterms:identifier: UST_Controlling_0022
- dcterms:description: Projektprognose zur Steuerung der SNB bzw. Konzern
- dcterms:modified: 2020-05-18T22:00:00.000Z
- dcterms:creator: Tamara Franke

## Realisierung - Prognose (SpecIF:UserStory)
- dcterms:identifier: UST_Controlling_0023
- dcterms:description: Projektprognose zum Aufdecken von Ressourcen auch anderer Bereiche und Geschäftsfelder
- dcterms:modified: 2020-05-18T22:00:00.000Z
- dcterms:creator: Tamara Franke

## Realisierung - Prognose (SpecIF:UserStory)
- dcterms:identifier: UST_Controlling_0024
- dcterms:description: Prognose: Projektbudgetanpassung  bei einer Projektbudgetüberschreitung ab x €.
- dcterms:modified: 2020-05-18T22:00:00.000Z
- dcterms:creator: Andreas Litwiakow

## Realisierung - Prognose (SpecIF:UserStory)
- dcterms:identifier: UST_Controlling_0025
- dcterms:description:
  - aktuelle Erkenntnisse projektscharf, jahresscheiben übergreifend prognostiziert, analog Detaillierung  Projektbeantragung
  - verbindlicher Zeithorizont Untersetzung angepasster Zielwerte
- dcterms:modified: 2020-05-18T22:00:00.000Z
- dcterms:creator: André Minke

## Realisierung - Prognose (SpecIF:UserStory)
- dcterms:identifier: UST_Controlling_0026
- dcterms:description: Jahresscheibe CAPEX / MuF-Opex:
  Plan <> Prognose / Ist
- dcterms:modified: 2020-05-18T22:00:00.000Z
- dcterms:creator: Dirk Baranowski

## Realisierung - Reporting (SpecIF:UserStory)
- dcterms:identifier: UST_Controlling_0027
- dcterms:description: Abweichungsanalyse Projekt  und  Aufwands/Ersatz-/Wachstumsinvestitions scharf
- dcterms:modified: 2020-05-18T22:00:00.000Z
- dcterms:creator: Andreas Litwiakow

## Realisierung - Reporting (SpecIF:UserStory)
- dcterms:identifier: UST_Controlling_0028
- dcterms:description: Ist- und Prognosewerte vs. Planwerte je Jahresscheibe sowie Gesamtlaufzeit; Prognose Gesamtlaufzeit vs. Budget
- dcterms:modified: 2020-05-18T22:00:00.000Z
- dcterms:creator: Roland Reball

## Realisierung - Reporting (SpecIF:UserStory)
- dcterms:identifier: UST_Controlling_0029
- dcterms:description: Reporting zu Abweichungen vom Plan während der Realisierung
- dcterms:modified: 2020-05-18T22:00:00.000Z
- dcterms:creator: Katarina Plamenac

## Realisierung - Reporting (SpecIF:UserStory)
- dcterms:identifier: UST_Controlling_0030
- dcterms:description: Antrag auf Budgetanpassungen beim Überschreiten von Wertgrenzen
- dcterms:modified: 2020-05-18T22:00:00.000Z
- dcterms:creator: Katarina Plamenac

## Realisierung - Reporting (SpecIF:UserStory)
- dcterms:identifier: UST_Controlling_0031
- dcterms:description: Transparenz bei wesentlichen Eingriffen z. B. aufgrund von Kürzungen inkl. Konsequenzen
- dcterms:modified: 2020-05-18T22:00:00.000Z
- dcterms:creator: Katarina Plamenac

## Realisierung - Reporting (SpecIF:UserStory)
- dcterms:identifier: UST_Controlling_0032
- dcterms:description: Ableiten von Aktivierungsstrategien/Aktivierungspotenzial
- dcterms:modified: 2020-05-18T22:00:00.000Z
- dcterms:creator: Tamara Franke

## Realisierung - Reporting (SpecIF:UserStory)
- dcterms:identifier: UST_Controlling_0033
- dcterms:description: Datenbereitstellung fürs Regelreporting (FFU, MRD), nicht nur Zahlen auch Inhalte
- dcterms:modified: 2020-05-18T22:00:00.000Z
- dcterms:creator: Dirk Baranowski

## Review - WiRe (SpecIF:UserStory)
- dcterms:identifier: UST_Controlling_0034
- dcterms:description: Investitionsprojekt ab einem IST-Finanzvolumen von 3,0 Mio. EUR; WiRe auf Basis des IST-Finanzstatus sowie die Darlegung der Finanz- und Realisierungsentwicklung je einzelner Jahresscheibe der Realisierungsphase.
- dcterms:modified: 2020-05-18T22:00:00.000Z
- dcterms:creator: Roland Reball

## Review - WiRe (SpecIF:UserStory)
- dcterms:identifier: UST_Controlling_0035
- dcterms:description: Review ab 3 MEUR, Mindestanforderung erneute WiRe
- dcterms:modified: 2020-05-18T22:00:00.000Z
- dcterms:creator: Katarina Plamenac

## Review - Ermittlung Wirtschaftlichkeit (SpecIF:UserStory)
- dcterms:identifier: UST_Controlling_0036
- dcterms:description: Wenn ich ein Controller wär, würde ich die Projektkosten- und Investitionen direkt den korrespondierenden Erlösen /Zuschüssen  gegenüberstellen, um die Wirtschaftlichkeit der Projekte bewerten zu können.
- dcterms:modified: 2020-05-18T22:00:00.000Z
- dcterms:creator: Jens Osdoba

## Review - Abweichungsanalyse (SpecIF:UserStory)
- dcterms:identifier: UST_Controlling_0037
- dcterms:description: Abweichungsanalyse Projekt  und  Aufwands/Ersatz-/Wachstumsinvestitions scharf
- dcterms:modified: 2020-05-18T22:00:00.000Z
- dcterms:creator: Andreas Litwiakow

## Top Down Einwirkung (Targetreduzierung) (SpecIF:UserStory)
- dcterms:identifier: UST_Controlling_0038
- dcterms:description: projektgenaue Zuordnungen von Einsparungen
- dcterms:modified: 2020-05-18T22:00:00.000Z
- dcterms:creator: Tamara Franke

## Top Down Einwirkung (Targetreduzierung) (SpecIF:UserStory)
- dcterms:identifier: UST_Controlling_0039
- dcterms:description: verbindlicher Zeithorizont Untersetzung angepasster Zielwerte
- dcterms:modified: 2020-05-18T22:00:00.000Z
- dcterms:creator: André Minke

## Top Down Einwirkung (Targetreduzierung) (SpecIF:UserStory)
- dcterms:identifier: UST_Controlling_0040
- dcterms:description: Dummies (Pauschale aus der Not) und Challenges (anspruchsvolle Ziele) unterscheiden
- dcterms:modified: 2020-05-18T22:00:00.000Z
- dcterms:creator: Katarina Plamenac

## Top Down Einwirkung (Targetreduzierung) (SpecIF:UserStory)
- dcterms:identifier: UST_Controlling_0041
- dcterms:description: Dummies sind nur Notlösung sehr spät im Prozess, müssen im Nachgang zeitnah von Verantwortlichen untersetzt werden
- dcterms:modified: 2020-05-18T22:00:00.000Z
- dcterms:creator: Katarina Plamenac

## Top Down Einwirkung (Targetreduzierung) (SpecIF:UserStory)
- dcterms:identifier: UST_Controlling_0042
- dcterms:description: Als Controller brauche ich eine Definition verschiedener Projekt-Datenstände. z.B. Prognose Q2, Challenge XY, um Diskussion über Abweichungen erleichtert zu führen
- dcterms:modified: 2020-05-18T22:00:00.000Z
- dcterms:creator: Christian Colberg

## Top Down Einwirkung (Targetreduzierung) (SpecIF:UserStory)
- dcterms:identifier: UST_Controlling_0043
- dcterms:description: Entscheidungsalternativen bewerten und zur Diskussion stellen
- dcterms:modified: 2020-05-18T22:00:00.000Z
- dcterms:creator: André Minke

## Top Down Einwirkung (Targetreduzierung) (SpecIF:UserStory)
- dcterms:identifier: UST_Controlling_0044
- dcterms:description: Vermeidung von Planungsdummies /Steuerungsdummies / Pauschalpositionen
- dcterms:modified: 2020-05-18T22:00:00.000Z
- dcterms:creator: Tamara Franke

## Top Down Einwirkung (Targetreduzierung) (SpecIF:UserStory)
- dcterms:identifier: UST_Controlling_0045
- dcterms:description: Aufzeigen von Konsequenzen aus Reduzierungen und Eingriffen ins Portfolio
- dcterms:modified: 2020-05-18T22:00:00.000Z
- dcterms:creator: Katarina Plamenac

## Top Down Einwirkung (Targetreduzierung) (SpecIF:UserStory)
- dcterms:identifier: UST_Controlling_0046
- dcterms:description: bevor Anpassungen in SAP erfolgen, erst ein stabiles Targetziel formulieren und abstimmen, dann agieren __> Ressourcen schonen im AS
- dcterms:modified: 2020-05-18T22:00:00.000Z
- dcterms:creator: Ronny Stark

## Top Down Einwirkung (Targetreduzierung) (SpecIF:UserStory)
- dcterms:identifier: UST_Controlling_0047
- dcterms:description: Präambel: Controlling informiert alle SNB-Stakeholder über veränderte Vorgaben und setzt diese in den relevanten Kontext
- dcterms:modified: 2020-05-18T22:00:00.000Z
- dcterms:creator: André Minke

## Top Down Einwirkung (Targetreduzierung) (SpecIF:UserStory)
- dcterms:identifier: UST_Controlling_0048
- dcterms:description: Priorisierung der Projekte erfolgt im Asset Management mit transparent nachvollziehbaren Entscheidungskriterien
- dcterms:modified: 2020-05-18T22:00:00.000Z
- dcterms:creator: Katarina Plamenac

## Top Down Einwirkung (Targetreduzierung) (SpecIF:UserStory)
- dcterms:identifier: UST_Controlling_0049
- dcterms:description: Überarbeitung des Projektportfolios mit Nennung der veränderten Projekte und aufzeigen der Konsequenzen
- dcterms:modified: 2020-05-18T22:00:00.000Z
- dcterms:creator: Andreas Litwiakow

## Top Down Einwirkung (Targetreduzierung) (SpecIF:UserStory)
- dcterms:identifier: UST_Controlling_0050
- dcterms:description: Anpassung (Reduzierung) des Projektportfolios unter Nennung der Folgen (Risiken) monetär und inhaltlich(technisch). Wirkung sowohl kurz-/ mittel- und langfristig ; Inkl. aufzeigen von Optionen
- dcterms:modified: 2020-05-18T22:00:00.000Z
- dcterms:creator: Dirk Baranowski

## Top Down Einwirkung (Targetreduzierung) (SpecIF:UserStory)
- dcterms:identifier: UST_Controlling_0051
- dcterms:description: Umsetzung der GF-Entscheidungen zur operativen Steuerung erfordert ggf.  die Steuerung einzelner Projekte
- dcterms:modified: 2020-05-18T22:00:00.000Z
- dcterms:creator: Roland Reball

## Top Down Einwirkung (Targetreduzierung) (SpecIF:UserStory)
- dcterms:identifier: UST_Controlling_0052
- dcterms:description: möglichst wenig über Dummies abbilden
- dcterms:modified: 2020-05-18T22:00:00.000Z
- dcterms:creator: Dirk Baranowski

## Top Down Einwirkung (Neue Konzernanforderungen) (SpecIF:UserStory)
- dcterms:identifier: UST_Controlling_0053
- dcterms:description: andere Terminpläne oder andere Reportinginhalte oder…
- dcterms:modified: 2020-05-18T22:00:00.000Z
- dcterms:creator: Katarina Plamenac

## Top Down Einwirkung (Externe Veränderungen Anpassungen an gesetzl. Neuregelungen) (SpecIF:UserStory)
- dcterms:identifier: UST_Controlling_0054
- dcterms:description: Veränderungen im Portfolio der SNB (Thema Drittgeschäft, Marktentwicklungen)
- dcterms:modified: 2020-05-18T22:00:00.000Z
- dcterms:creator: Tamara Franke

## Top Down Einwirkung (Externe Veränderungen Anpassungen an gesetzl. Neuregelungen) (SpecIF:UserStory)
- dcterms:identifier: UST_Controlling_0055
- dcterms:description: Betrachtungen der gesellschaftl. Entwicklungen, Wachstum der Stadt, Konsumverhalten, Politik
- dcterms:modified: 2020-05-18T22:00:00.000Z
- dcterms:creator: Tamara Franke

## Top Down Einwirkung (interne (SNB / VATTENFALL) Veränderungen aus dem Risikomanagement / Betrachtungen aus der Störentwicklung) (SpecIF:UserStory)
- dcterms:identifier: UST_Controlling_0056
- dcterms:description: Anforderungen der Revision umsetzen
- dcterms:modified: 2020-05-18T22:00:00.000Z
- dcterms:creator: Tamara Franke

## Top Down Einwirkung (interne (SNB / VATTENFALL) Veränderungen aus dem Risikomanagement / Betrachtungen aus der Störentwicklung) (SpecIF:UserStory)
- dcterms:identifier: UST_Controlling_0057
- dcterms:description: Jahresuhr
- dcterms:modified: 2020-05-18T22:00:00.000Z
- dcterms:creator: Tamara Franke

## Top Down Einwirkung (Projektschließung Anforderungen ans einzelne Projekt und ans Projektportfolio) (SpecIF:UserStory)
- dcterms:identifier: UST_Controlling_0058
- dcterms:description: Jahresprojekte, einjährige Projekte, wiederkehrende Projekte --> sollten dem zeitl. Namen entsprechen
- dcterms:modified: 2020-05-18T22:00:00.000Z
- dcterms:creator: Tamara Franke

## Top Down Einwirkung (Umschichtung Aufwand / Invest) (SpecIF:UserStory)
- dcterms:identifier: UST_Controlling_0059
- dcterms:modified: 2020-05-18T22:00:00.000Z

## Bottom Up (Budgeterhöhung Mehrleistung / Verteuerung …) (SpecIF:UserStory)
- dcterms:identifier: UST_Controlling_0060
- dcterms:description: Abweichungsbegründung und neuen Prognosestand
- dcterms:modified: 2020-05-18T22:00:00.000Z
- dcterms:creator: Andreas Litwiakow

## Bottom Up (Budgeterhöhung Mehrleistung / Verteuerung …) (SpecIF:UserStory)
- dcterms:identifier: UST_Controlling_0061
- dcterms:description: Aufzeigen der Auswirkungen auf das Projektportfolio (Abhängigkeiten von Projekten  unter einander)
- dcterms:modified: 2020-05-18T22:00:00.000Z
- dcterms:creator: Andreas Litwiakow

## Bottom Up (Budgeterhöhung Mehrleistung / Verteuerung …) (SpecIF:UserStory)
- dcterms:identifier: UST_Controlling_0062
- dcterms:description: Projektbudgetnachbewilligung, inkl. Des Aufzeigens der Konsequenzen, wenn es welche im Projektportfolio gibt.
- dcterms:modified: 2020-05-18T22:00:00.000Z
- dcterms:creator: Andreas Litwiakow

## Bottom Up (Budgeterhöhung Mehrleistung / Verteuerung …) (SpecIF:UserStory)
- dcterms:identifier: UST_Controlling_0063
- dcterms:description: frühzeitiges Anzeigen von zusätzlichem Budgetbedarf
- dcterms:modified: 2020-05-18T22:00:00.000Z
- dcterms:creator: André Minke

## Bottom Up (Budgeterhöhung Mehrleistung / Verteuerung …) (SpecIF:UserStory)
- dcterms:identifier: UST_Controlling_0064
- dcterms:description: Entscheidungsalternativen bewerten
- dcterms:modified: 2020-05-18T22:00:00.000Z
- dcterms:creator: André Minke

## Bottom Up (Budgeterhöhung Mehrleistung / Verteuerung …) (SpecIF:UserStory)
- dcterms:identifier: UST_Controlling_0065
- dcterms:description: Betrachtung der Wirtschaftlichkeit durch die veränderte Entwicklung (auch mögliche Budgetanpassungen initiieren)
- dcterms:modified: 2020-05-18T22:00:00.000Z
- dcterms:creator: Dirk Baranowski

## Bottom Up (Budgeterhöhung Mehrleistung / Verteuerung …) (SpecIF:UserStory)
- dcterms:identifier: UST_Controlling_0066
- dcterms:description: die "bekannte" breite Palette der Abweichungstreiber in der Realisierungsphase
- dcterms:modified: 2020-05-18T22:00:00.000Z
- dcterms:creator: Roland Reball

## Bottom Up (Budgeterhöhung Mehrleistung / Verteuerung …) (SpecIF:UserStory)
- dcterms:identifier: UST_Controlling_0067
- dcterms:description: Welche Projekte "sponsoren" die Verteuerung (bei unveränderter Verzielung -> Jahressicht
- dcterms:modified: 2020-05-18T22:00:00.000Z
- dcterms:creator: Dirk Baranowski

## Bottom Up (Budgeterhöhung Mehrleistung / Verteuerung …) (SpecIF:UserStory)
- dcterms:identifier: UST_Controlling_0068
- dcterms:description: Betrachtung der Wirtschaftlichkeit durch die veränderte Entwicklung
- dcterms:modified: 2020-05-18T22:00:00.000Z
- dcterms:creator: Dirk Baranowski

## Bottom Up (Budgetverschiebung in Jahresscheibe) (SpecIF:UserStory)
- dcterms:identifier: UST_Controlling_0069
- dcterms:description: Abweichungsbegründung und neuen Prognosestand
- dcterms:modified: 2020-05-18T22:00:00.000Z
- dcterms:creator: Andreas Litwiakow

## Bottom Up (Terminverschiebung ) (SpecIF:UserStory)
- dcterms:identifier: UST_Controlling_0070
- dcterms:description: Abweichungsbegründung und neuen Prognosestand
- dcterms:modified: 2020-05-18T22:00:00.000Z
- dcterms:creator: Andreas Litwiakow

## Bottom Up (Materialengpässe, Mat.veränderungen, Kapazitätsprobleme) (SpecIF:UserStory)
- dcterms:identifier: UST_Controlling_0071
- dcterms:description: techn. Überarbeitung von Projekten
- dcterms:modified: 2020-05-18T22:00:00.000Z
- dcterms:creator: Tamara Franke

## Beantragung - Dokumentation Beantragung (SpecIF:UserStory)
- dcterms:identifier: UST_Controlling_0072
- dcterms:description: Als Controller benötige ich zur Genehmigung von Projekten, einen Projektantrag der eine Beschreibung des Projektes, den Ergebnissen der WiRe, die kaufmännischen Stammdaten, den Originalplan PSP-Elementen, Geschäftsjahres und Kostenarten genau, einer Managementzusammenfassung der Beschreibung sowie die Unterschriften des Projektleiters, Projektverantwortlichen und Abteilungsleiter des Verantwortlichen Bereiches enthält.
- dcterms:modified: 2020-01-17T22:00:00.000Z
- dcterms:creator: Andreas Litwiakow

## Beantragung - Dokumentation Beantragung (SpecIF:UserStory)
- dcterms:identifier: UST_Controlling_0073
- dcterms:description: Als Controller benötige ich zur Projektbeantragung bei der Vattenfall Europe GmbH die Projektplanung der SNB aufgeteilt in Aufwand, Ersatz- und Wachstumsinvestitionen pro Jahr für die nächsten 5 Jahre sowie einen Projektsteckbrief für die Projekte mit einem Finanzvolumen größer 10 Millionen Euros.
- dcterms:modified: 2020-01-17T22:00:00.000Z
- dcterms:creator: Andreas Litwiakow

## Realisierung - Reporting (SpecIF:UserStory)
- dcterms:identifier: UST_Controlling_0074
- dcterms:description: Als Controller benötige ich für das Reporting an die BA und innerhalb der Stromnetz die Abweichungsbegründungen pro Monat für die Differenz zwischen IST und dem kumulierten Plan.
- dcterms:modified: 2020-01-17T22:00:00.000Z
- dcterms:creator: Andreas Litwiakow

## Realisierung - Prognose (SpecIF:UserStory)
- dcterms:identifier: UST_Controlling_0075
- dcterms:description: Um die Projektprognose gemeinsam mit den SAP-Administratoren kordieren (Öffnen, schließen, Projektabrechnung, Ausbucher buchen, …) zu können, benötige ich als Controller von den zuständigen N2-Bereichen die entsprechenden Informationen zu den jeweiligen Zeitpunkten.
- dcterms:modified: 2020-01-17T22:00:00.000Z
- dcterms:creator: Andreas Litwiakow

## Geschäftsprozesse (SpecIF:Heading)
- dcterms:type: SpecIF:BusinessProcesses

## Modellelemente (Glossar) (SpecIF:Heading)
- dcterms:type: SpecIF:Glossary

## Akteure (SpecIF:Heading)

## Zustände (SpecIF:Heading)

## Ereignisse (SpecIF:Heading)

## Kollektionen und Gruppen (SpecIF:Heading)

## Portfoliomanagement (User-Stories) (SpecIF:Outline)

## Portfoliomanagement (SpecIF:Heading)

## Bewertung neuer Projekte (Finanzraten, Mengen auf BM/BMT/BMG, Varianten)_A (SpecIF:UserStory)
- dcterms:identifier: UST_PortfolioMgmt_0074a
- dcterms:description: Als Portfoliomanager (Asset-Management) möchte ich für neue Projekte Finanzraten, Mengen auf BM/BMT/BMG-Ebene je Jahresscheibe sowie Funktionalitäten, Abhängigkeiten und Varianten auswerten um eine Bewertung in RBAM durchzuführen sowie die Priorisierung im Projektprogramm, die Bewertung der Risikoverdrängung und Mittelbeschaffung vornehmen zu können.
- SpecIF:Priority: 1_hoch
- dcterms:modified: 2020-06-09T22:00:00.000Z
- dcterms:creator: Nina Fehse

## Bewertung neuer Projekte (Finanzraten, Mengen auf BM/BMT/BMG, Varianten)_B (SpecIF:UserStory)
- dcterms:identifier: UST_PortfolioMgmt_0074b
- dcterms:description: Als Portfoliomanager (Asset-Management) möchte ich für neue Projekte Finanzraten, Mengen auf BM/BMT/BMG-Ebene je Jahresscheibe sowie Funktionalitäten, Abhängigkeiten und Varianten auswerten um Eine Bewertung des Projektportfolios  als Ganzes ist notwendig um Zielgrößen technische (Zustand D; SAIDI, Anlagensubstanz) und wirtschaftlich (CAPEX, OPEX, NNE) langfristig zu prognostizieren.
- SpecIF:Priority: 1_hoch
- dcterms:modified: 2020-06-09T22:00:00.000Z
- dcterms:creator: Michael Zeller

## Zuschüsse in der WiRe berücksichtigen (SpecIF:UserStory)
- dcterms:identifier: UST_PortfolioMgmt_0077
- dcterms:description: Als Portfoliomanager (Asset-Management) / Controlling möchte ich die Zuschüsse zu Kundenprojekten im Rahmen der WiRe hinterlegen um die Wirtschaftlichkeit des Projektes berechnen zu können.
- SpecIF:Priority: 1_hoch
- dcterms:modified: 2020-06-09T22:00:00.000Z
- dcterms:creator: Bettina Brückner

## Risikoparameter für RBAM berücksichtigen (SpecIF:UserStory)
- dcterms:identifier: UST_PortfolioMgmt_0075
- dcterms:description: Als Portfoliomanager (Asset-Management) möchte ich Daten in das Risikoregister aufnehmen und Risikoparameter erhalten um die Grundlage für RBAM (Bewertung Risikoverdrängung u. Priorisierung von Projekten) zu erhalten und die Erfüllung der Anforderungen an das Risikomanagement gem. ISO 55 000 zu gewährleisten.
- SpecIF:Priority: 1_hoch
- dcterms:modified: 2020-06-09T22:00:00.000Z
- dcterms:creator: Nina Fehse, Michael Zeller

## Übersicht Projektplanung auswerten (SpecIF:UserStory)
- dcterms:identifier: UST_PortfolioMgmt_0076
- dcterms:description: Als Portfoliomanager (Asset-Portfoliomanagement) möchte ich eine Übersicht der aktuellen Projekt-Planung und Prognose haben um die Planung und Mittelfristplanung erstellen und auswerten zu können.
- SpecIF:Priority: 1_hoch
- dcterms:modified: 2020-06-09T22:00:00.000Z
- dcterms:creator: Alexandra Müller

## Daten für Kapitalkostenantrag (KKA) auswerten (SpecIF:UserStory)
- dcterms:identifier: UST_PortfolioMgmt_0053
- dcterms:description: Als Portfoliomanager (Asset-Management) möchte ich den technischen Status der Projekte mit dem aktuellen Inbetriebnahmetermin monitoren um die Daten für den Kapitalkostenantrag (KKA) erzeugen zu können.
- SpecIF:Priority: 1_hoch
- dcterms:modified: 2020-06-09T22:00:00.000Z
- dcterms:creator: Alexandra Müller

## Mittelfristplanung und KKA erstellen (SpecIF:UserStory)
- dcterms:identifier: UST_PortfolioMgmt_NEU1
- dcterms:description: Als Portfoliomanager (Asset-Portfoliomanagement) möchte ich Typicals BM-scharf für Mittelfristplanung und KKA-Berechnung anlegen um Mittelfristplanung und KKA zu erstellen.
- SpecIF:Priority: 1_hoch
- dcterms:modified: 2020-06-09T22:00:00.000Z
- dcterms:creator: Alexandra Müller

## Auswertung steuerungsrelevanter Kennzahlen (SpecIF:UserStory)
- dcterms:identifier: UST_PortfolioMgmt_0050
- dcterms:description: Als Portfoliomanager (Asset-Management) möchte ich das Projekt-Portfolio (SNB) mit den steuerungsrelevanten Kennzahlen monitoren um den effizienten Einsatz der verfügbaren finanziellen Mittel steuern zu können.
- SpecIF:Priority: 1_hoch
- dcterms:modified: 2020-06-09T22:00:00.000Z
- dcterms:creator: Christian Küfner, Nicole Hentschel

## Daten der Feinplanung in WiRe berücksichtigen (SpecIF:UserStory)
- dcterms:identifier: UST_PortfolioMgmt_NEU2
- dcterms:description: Als Portfoliomanager (Asset-Management) möchte ich die WiRe mit Daten der Feinplanung (Kalkulationsschema komplett) speisen um die Wirtschaftlichkeit des Projektes nach der Feinplanung für die Bereitstellung der Projektanträge = Ende der Konzeption/ Beginn der Realisierung zu bestimmen.
- SpecIF:Priority: 1_hoch
- dcterms:modified: 2020-06-09T22:00:00.000Z
- dcterms:creator: Bettina Brückner

## Daten aus dem Projektprogramm und unterjähriger Projekte in WiRe berücksichtigen (SpecIF:UserStory)
- dcterms:identifier: UST_PortfolioMgmt_0074
- dcterms:description: Als Portfoliomanager (Asset-Management) möchte ich die WiRe mit Daten aus dem Projektprogramm oder aus der Betrachtung unterjähriger Projekte speisen um den Nachweis der Wirtschaftlichkeit zu erhalten und die konsistente Priorisierung des Projektprogramms vornehmen zu können.
- SpecIF:Priority: 1_hoch
- dcterms:modified: 2020-06-09T22:00:00.000Z
- dcterms:creator: Bettina Brückner

## Kaufmännische Kennzahlen entsprechend des Kalkulationsmodells bei Steuerung Asset eigener Produkte berücksichtigen (SpecIF:UserStory)
- dcterms:identifier: UST_PortfolioMgmt_0026a/b
- dcterms:description: Als Portfoliomanager (Asset-Management) möchte ich die kaufmännischen Kennzahlen entsprechend des Kalkulationsmodells für Projekte sehen können um die kaufmännische Steuerung der Asset eigenen Projekte durchführen zu können.
- SpecIF:Priority: 1_hoch
- dcterms:modified: 2020-06-09T22:00:00.000Z
- dcterms:creator: Nicole Hentschel, Anne Ebelt

## Projektstatus für Abweichungsanalysen auswerten (SpecIF:UserStory)
- dcterms:identifier: UST_PortfolioMgmt_0092
- dcterms:description: Als  Portfoliomanager (Asset Management) möchte ich den Projektstatus anhand von Kommentaren und technischen Statusmeldungen monitoren um Abweichungsanalysen durchführen und konsolidiert weitergeben zu können.
- SpecIF:Priority: 1_hoch
- dcterms:modified: 2020-06-09T22:00:00.000Z
- dcterms:creator: Nicole Hentschel

## Auswertungsmöglichkeit historischer Daten für Planung und Prognose (SpecIF:UserStory)
- dcterms:identifier: UST_PortfolioMgmt_0024
- dcterms:description: Als  Portfoliomanager (Asset Management) möchte ich historische Datenbestände für Planung und Prognose sehen können Veränderungen des Projektportfolios erkennen zu können.
- SpecIF:Priority: 1_hoch
- dcterms:modified: 2020-06-09T22:00:00.000Z
- dcterms:creator: Christian Küfner, Nicole Hentschel

## WiRe und Grobplanung in TWE integrieren (SpecIF:UserStory)
- dcterms:identifier: UST_PortfolioMgmt_0079
- dcterms:description: Als  Portfoliomanager (Asset Management) möchte ich die WiRe und die Ergebnisse der Grobplanung in die TWE integrieren um die Wirtschaftlichkeit des Projektes nach der Grobplanung neu zu bestimmen.
- SpecIF:Priority: 1_hoch
- dcterms:modified: 2020-06-09T22:00:00.000Z
- dcterms:creator: Bettina Brückner, Christian Küfner

## Projektstatus einsehen (SpecIF:UserStory)
- dcterms:identifier: UST_PortfolioMgmt_0073
- dcterms:description: Als  Portfoliomanager (Asset Management) möchte ich zu jedem Zeitpunkt den Projektstatus pro Projektphase sehen können um den Überblick über das aktive Projektportfolio zu bekommen.
- SpecIF:Priority: 1_hoch
- dcterms:modified: 2020-06-09T22:00:00.000Z
- dcterms:creator: Christian Küfner

## Geschäftsprozesse (SpecIF:Heading)
- dcterms:type: SpecIF:BusinessProcesses

## Modellelemente (Glossar) (SpecIF:Heading)
- dcterms:type: SpecIF:Glossary

## Akteure (SpecIF:Heading)

## Zustände (SpecIF:Heading)

## Ereignisse (SpecIF:Heading)

## Kollektionen und Gruppen (SpecIF:Heading)

## Portfoliomanagement (Anforderungen) (SpecIF:Outline)

## Portfoliomanagement (SpecIF:Heading)

## REQ_PortfolioMgmt_1 - 'Titel' (IREB:Requirement)
- dcterms:identifier: REQ_PortfolioMgmt_1
- dcterms:subject: PSID 43a
- dcterms:description: PSID 43a: Neue Projekte benötigen Detailgrad:
  Mengen je Einzelprojekt auf BM-/BMT-/BMG-Ebene auf jeweiligen Jahresscheiben jeweils separat für zugebaute als auch demontierte BM (inkl. Zustand des jeweiligen BM)
        → Bewertung der Risikoverdrängung des Projektes und Mittelbeschaffung
  Information über Funktion des Projektes (1-zu-1-Ersatz oder erweiterte Funktionalität)
  notwendiger Vorgänger/Nachfolger (um Abhängigkeiten nachvollziehen zu können)
        → gemeinsame Bewertung Abhängiger Projekte in RBAM
  Alternativen/Varianten für jedes Projekt
  NNE und Projektkosten jahresscheibenscharf aus WiReBM: konkretes Betriebsmittel, BMT: Betriebsmitteltyp, BMG: Betriebsmittelgruppe, RBAM: Risk Based Asset Management (Priorisierungsmethode), WiRe: Wirtschaftlichkeitsrechnung, NNE: Netznutzungsentgelte
- IREB:RequirementType: Funktion
- SpecIF:Priority: 1_hoch
- dcterms:modified: 2020-06-09T22:00:00.000Z
- dcterms:creator: Nina Fehse

## REQ_PortfolioMgmt_2 - 'Titel' (IREB:Requirement)
- dcterms:identifier: REQ_PortfolioMgmt_2
- dcterms:subject: PSID 43b
- dcterms:description: PSID 43b: Projektimpulse benötigen bei erster Idee den Detailgrad:
  Mengen je Einzelprojekt auf BM-/BMT-/BMG-Ebene auf jeweiligen Jahresscheiben jeweils separat für zugebaute als auch demontierte BMT
        → Bewertung der Risikoverdrängung des Projektes und Mittelbeschaffung
  Information über Funktion des Projektes (1-zu-1-Ersatz oder erweiterte Funktionalität)
  Projektkosten jahresscheibenscharf aus WiReBM: konkretes Betriebsmittel, BMT: Betriebsmitteltyp, BMG: Betriebsmittelgruppe, RBAM: Risk Based Asset Management (Priorisierungsmethode), WiRe: Wirtschaftlichkeitsrechnung, NNE: Netznutzungsentgelte
- IREB:RequirementType: Funktion
- SpecIF:Priority: 1_hoch
- dcterms:modified: 2020-06-09T22:00:00.000Z
- dcterms:creator: Nina Fehse

## REQ_PortfolioMgmt_3 - 'Titel' (IREB:Requirement)
- dcterms:identifier: REQ_PortfolioMgmt_3
- dcterms:subject: PSID 72
- dcterms:description: PSID 72: Aktualisierung der Kosten-/ Mengenkalkulation
- IREB:RequirementType: Funktion
- SpecIF:Priority: 1_hoch
- dcterms:modified: 2020-06-09T22:00:00.000Z
- dcterms:creator: Christian Küfner, Nicole Hentschel

## REQ_PortfolioMgmt_4 - 'Titel' (IREB:Requirement)
- dcterms:identifier: REQ_PortfolioMgmt_4
- dcterms:subject: PSID 235
- dcterms:description: PSID 235: Obligo jahresscharf, Steuerung
- IREB:RequirementType: Funktion
- SpecIF:Priority: 1_hoch
- dcterms:modified: 2020-06-09T22:00:00.000Z
- dcterms:creator: Christian Küfner, Nicole Hentschel

## REQ_PortfolioMgmt_5 - 'Titel' (IREB:Requirement)
- dcterms:identifier: REQ_PortfolioMgmt_5
- dcterms:description: 4 Sektoren: Finanzen, Qualität/Leistung, Prozesse und Assetnachhaltigkeit (Top-Down)
- IREB:RequirementType: Funktion
- SpecIF:Priority: 1_hoch
- dcterms:modified: 2020-06-09T22:00:00.000Z
- dcterms:creator: Christian Küfner, Nicole Hentschel

## REQ_PortfolioMgmt_6 - 'Titel' (IREB:Requirement)
- dcterms:identifier: REQ_PortfolioMgmt_6
- dcterms:description: Wesentliche Kennzahlen sind aktuell CAPEX  oder MuF-Aufwand
- IREB:RequirementType: Funktion
- SpecIF:Priority: 1_hoch
- dcterms:modified: 2020-06-09T22:00:00.000Z
- dcterms:creator: Christian Küfner, Nicole Hentschel

## REQ_PortfolioMgmt_7 - 'Titel' (IREB:Requirement)
- dcterms:identifier: REQ_PortfolioMgmt_7
- dcterms:description: Wesentliche Kennzahlen sind aktuell CAPEX  oder MuF-Aufwand
- IREB:RequirementType: Funktion
- SpecIF:Priority: 1_hoch
- dcterms:modified: 2020-06-09T22:00:00.000Z
- dcterms:creator: Christian Küfner, Nicole Hentschel

## REQ_PortfolioMgmt_8 - 'Titel' (IREB:Requirement)
- dcterms:identifier: REQ_PortfolioMgmt_8
- dcterms:description: Prognoseplausibilisierung Jahressicht (Prognose vs. Verfügt + erwartete Zuschläge + erwartete dir. PK) inkl. Hochrechnung basierend auf historischen Daten (z.B. typische Verschiebung vs. Jahresplan). Ggfs. Tool-unterstützte Abfragen beim Asset Service, Kommentierungen offen für SNB
- IREB:RequirementType: Funktion
- SpecIF:Priority: 1_hoch
- dcterms:modified: 2020-06-09T22:00:00.000Z
- dcterms:creator: Andre Minke

## REQ_PortfolioMgmt_9 - 'Titel' (IREB:Requirement)
- dcterms:identifier: REQ_PortfolioMgmt_9
- dcterms:subject: PSID 59
- dcterms:description: PSID 59: Zahlungsreihe  = Erlöse pro Jahr / Finanzraten
  Msdf
- IREB:RequirementType: Funktion
- SpecIF:Priority: 1_hoch
- dcterms:modified: 2020-06-09T22:00:00.000Z
- dcterms:creator: Bettina Brückner

## REQ_PortfolioMgmt_10 - 'Titel' (IREB:Requirement)
- dcterms:identifier: REQ_PortfolioMgmt_10
- dcterms:subject: PSID 44
- dcterms:description: PSID 44: Jahresscheiben, Finanzraten nach HGB (Projektkosten) notwendig!
- IREB:RequirementType: Funktion
- SpecIF:Priority: 1_hoch
- dcterms:modified: 2020-06-09T22:00:00.000Z
- dcterms:creator: Bettina Brückner

## REQ_PortfolioMgmt_11 - 'Titel' (IREB:Requirement)
- dcterms:identifier: REQ_PortfolioMgmt_11
- dcterms:subject: PSID 53
- dcterms:description: PSID 53: benötigte Daten für Risikoregister:
  SAIDI Informationen BMT-scharf: Störraten, CAIDI, ausgefallene Bemessungsscheinleistung (HS und MS)/Kundenanzahl (NS), insg. Kundenanzahl (NS) und Bemessungsscheinleistung (MS/HS) des Netzes
  Information bezüglich "Sonderstörungen" BM-scharf wie z.B. Gruppenausfälle, 8D2-SA Störung durch Undichtigkeit, Trafobrand ... (welches BM war betroffen und was hat dazu geführt und welche weiteren BM sind dadurch betroffen)
  Bestand der Betriebsmittel BMT-scharf inkl. Alter und Zustand → muss flexibel anpassbar sein
  Prognose der Betriebsmittelentwicklung und Störungen aus Asset Simulation
  durchschnittliche EOIS Kosten pro Störung eines BMT
  PLAN-IST-Abgleich von Anzahl der IH-Maßnahmen je BMT
  Anzahl und Datum für IH und Inspektion BM-scharf, welche IH-Strategie wird angewendet (turnusmäßig/zustandsabhängig/...)
  BMT: Betriebsmitteltyp, EOIS: ereignisorientierte Instandhaltung
- IREB:RequirementType: Funktion
- SpecIF:Priority: 1_hoch
- dcterms:modified: 2020-06-09T22:00:00.000Z
- dcterms:creator: Nina Fehse, Michael Zeller

## REQ_PortfolioMgmt_12 - 'Titel' (IREB:Requirement)
- dcterms:identifier: REQ_PortfolioMgmt_12
- dcterms:subject: PSID 129
- dcterms:description: PSID 129: stetige, regelmäßige Prognose der Folgejahre, Aktualisierung der Prognosen (Folgejahre!) (Akt. Kosten, Akt. Mengen)
  Planung und Prognose für 5 und 10 Jahre
  Kosten (HGB und IFRS) nach Kalkulationsschema
  Unterscheidung nach Invest/Aufwand 
  Unterscheidung nach BMG, Ersatz, Erweiterung, Invest und Aufwand, Vertrag, Bereich, Laufzeiten, Kosten pro Jahr in LZ
  Abbildungen aller SNB-Projekte (mit und ohne KTO)
- IREB:RequirementType: Funktion
- SpecIF:Priority: 1_hoch
- dcterms:modified: 2020-06-09T22:00:00.000Z
- dcterms:creator: Alexandra Müller

## REQ_PortfolioMgmt_13 - 'Titel' (IREB:Requirement)
- dcterms:identifier: REQ_PortfolioMgmt_13
- dcterms:subject: PSID 42
- dcterms:description: PSID 42: Extrahierung unterschiedlicher Datenstände zu jedem Zeitpunkt (historische Datenbestände) je Projekt und BMG (2. und 3. Projektstufe)
  Verschiedene Planversionen notwendig (Planung AMC AS, Beauftragung, Prognosestände)
- IREB:RequirementType: Funktion
- SpecIF:Priority: 1_hoch
- dcterms:modified: 2020-06-09T22:00:00.000Z
- dcterms:creator: Alexandra Müller

## REQ_PortfolioMgmt_14 - 'Titel' (IREB:Requirement)
- dcterms:identifier: REQ_PortfolioMgmt_14
- dcterms:subject: PSID 84
- dcterms:description: PSID 84: geplanten IBN-Datum tracken (Inbetriebnahmedatum)
  Laufzeiten der Projekte (Kosten pro Jahr)
- IREB:RequirementType: Funktion
- SpecIF:Priority: 1_hoch
- dcterms:modified: 2020-06-09T22:00:00.000Z
- dcterms:creator: Alexandra Müller

## REQ_PortfolioMgmt_15 - 'Titel' (IREB:Requirement)
- dcterms:identifier: REQ_PortfolioMgmt_15
- dcterms:subject: PSID 44
- dcterms:description: PSID 44: Projekte benötigen Detailgrad: Jahresscheiben, BM-Ebene, Finanzraten, Aktivierungszeitpunkt, Kosten nach HGB notwendig!
- IREB:RequirementType: Funktion
- SpecIF:Priority: 1_hoch
- dcterms:modified: 2020-06-09T22:00:00.000Z
- dcterms:creator: Alexandra Müller

## REQ_PortfolioMgmt_16 - 'Titel' (IREB:Requirement)
- dcterms:identifier: REQ_PortfolioMgmt_16
- dcterms:subject: PSID 128
- dcterms:description: PSID 128: IBN-Datum prüfen und ggf. justieren
- IREB:RequirementType: Funktion
- SpecIF:Priority: 1_hoch
- dcterms:modified: 2020-06-09T22:00:00.000Z
- dcterms:creator: Alexandra Müller

## REQ_PortfolioMgmt_17 - 'Titel' (IREB:Requirement)
- dcterms:identifier: REQ_PortfolioMgmt_17
- dcterms:subject: PSID 129
- dcterms:description: PSID 129: stetige, in regelmäßigen Prognosen, Aktualisierung der Prognosen (Akt. Kosten, Akt. Mengen)
  Planung und Prognose für 5 Jahre
  Kosten Invest (HGB) nach Kalkulationsschema
  Unterscheidung nach BMG (Basis zum Brücken auf Anlagenklassen) 
  Abbildungen aller SNB-Projekte Invest (mit und ohne KTO)
  AiB-Tracking (Anteil Aktivierung und AiB im IST eines Jahres)
- IREB:RequirementType: Funktion
- SpecIF:Priority: 1_hoch
- dcterms:modified: 2020-06-09T22:00:00.000Z
- dcterms:creator: Alexandra Müller

## REQ_PortfolioMgmt_18 - 'Titel' (IREB:Requirement)
- dcterms:identifier: REQ_PortfolioMgmt_18
- dcterms:subject: PSID 42
- dcterms:description: PSID 42: Extrahierung unterschiedlicher Datenstände zu jedem Zeitpunkt (historische Datenbestände) je Projekt und BMG (2. und 3. Projektstufe)
  Verschiedene Planversionen
- IREB:RequirementType: Funktion
- SpecIF:Priority: 1_hoch
- dcterms:modified: 2020-06-09T22:00:00.000Z
- dcterms:creator: Alexandra Müller

## REQ_PortfolioMgmt_19 - 'Titel' (IREB:Requirement)
- dcterms:identifier: REQ_PortfolioMgmt_19
- dcterms:description: Anlagengruppen der BNetzA zur Verknüpfung mit Anlagenklassen der SNB
- IREB:RequirementType: Funktion
- SpecIF:Priority: 1_hoch
- dcterms:modified: 2020-06-09T22:00:00.000Z
- dcterms:creator: Anne Ebelt

## REQ_PortfolioMgmt_20 - 'Titel' (IREB:Requirement)
- dcterms:identifier: REQ_PortfolioMgmt_20
- dcterms:subject: PSID 214
- dcterms:description: PSID 214: Typicals anlegen BM-scharf für Mittelfristplanung und KKA Berechnung
- IREB:RequirementType: Funktion
- SpecIF:Priority: 1_hoch
- dcterms:modified: 2020-06-09T22:00:00.000Z
- dcterms:creator: Alexandra Müller

## REQ_PortfolioMgmt_21 - 'Titel' (IREB:Requirement)
- dcterms:identifier: REQ_PortfolioMgmt_21
- dcterms:subject: PSID 42
- dcterms:description: PSID 42: Extrahierung unterschiedlicher Datenstände zu jedem Zeitpunkt (historische Datenbestände) je Projekt und BMG (2. und 3. Projektstufe)
  Verschiedene Planversionen
- IREB:RequirementType: Funktion
- SpecIF:Priority: 1_hoch
- dcterms:modified: 2020-06-09T22:00:00.000Z
- dcterms:creator: Alexandra Müller

## REQ_PortfolioMgmt_22 - 'Titel' (IREB:Requirement)
- dcterms:identifier: REQ_PortfolioMgmt_22
- dcterms:subject: PSID 129
- dcterms:description: PSID 129: stetige, in regelmäßigen Prognosen, Aktualisierung der Prognosen (Akt. Kosten, Akt. Mengen)
  Planung und Prognose für 5 und 10 Jahre
  Kosten (HGB und IFRS) nach Kalkulationsschema
  Unterscheidung nach Invest/Aufwand 
  Unterscheidung nach BMG
  Abbildungen aller SNB-Projekte (mit und ohne KTO)
- IREB:RequirementType: Funktion
- SpecIF:Priority: 1_hoch
- dcterms:modified: 2020-06-09T22:00:00.000Z
- dcterms:creator: Alexandra Müller

## REQ_PortfolioMgmt_23 - 'Titel' (IREB:Requirement)
- dcterms:identifier: REQ_PortfolioMgmt_23
- dcterms:subject: PSID 111a
- dcterms:description: PSID 111a: Parameter WiRe mit Daten Feinplanung speisen - > genaue Indikation wirtschaftliche Beurteilung Einzelprojektprogramm auf Basis IRR und NPV, Detailgrad: CAPEX/OPEX, alle Jahresscheiben/Finanzraten, BMG-Ebene, Erlöse/Zuschüsse,  Neubau und Demontage etc
  neue Projekte benötigen Detailgrad: Jahresscheiben, BM-Ebene, Finanzraten für Opex und Capex für IFRS und HGB;
  WiRe, Nachweis der Wirtschaftlichkeit im aktuell gültigen Regulierungsmodell, Priorisierung im Portfolio anhand der Höhe des IRR – Input für RBAM, Langfristplanung zur Mittelbeschaffung, Konsistente Priorisierung des Projektprogramms
- IREB:RequirementType: Funktion
- SpecIF:Priority: 1_hoch
- dcterms:modified: 2020-06-09T22:00:00.000Z
- dcterms:creator: Bettina Brückner

## REQ_PortfolioMgmt_24 - 'Titel' (IREB:Requirement)
- dcterms:identifier: REQ_PortfolioMgmt_24
- dcterms:description: Kalkulationsschema muss vollständig abgebildet sein (--> Definition von Vollständigkeit ergänzen WAS bedeutet vollständig?) --> bis zur Stufe Bereichskosten und Projektkosten, Kalkulationsschema komplett
- IREB:RequirementType: Funktion
- SpecIF:Priority: 1_hoch
- dcterms:modified: 2020-06-09T22:00:00.000Z
- dcterms:creator: Christian Küfner

## REQ_PortfolioMgmt_25 - 'Titel' (IREB:Requirement)
- dcterms:identifier: REQ_PortfolioMgmt_25
- dcterms:subject: PSID 43
- dcterms:description: PSID 43: neue Projekte benötigen Detailgrad: Jahresscheiben, BM-Ebene, Finanzraten für Opex und Capex für IFRS und HGB;
- IREB:RequirementType: Funktion
- SpecIF:Priority: 1_hoch
- dcterms:modified: 2020-06-09T22:00:00.000Z
- dcterms:creator: Bettina Brückner

## REQ_PortfolioMgmt_26 - 'Titel' (IREB:Requirement)
- dcterms:identifier: REQ_PortfolioMgmt_26
- dcterms:subject: PSID 43 b
- dcterms:description: PSID 43 b: WiRe, Nachweis der Wirtschaftlichkeit im aktuell gültigen Regulierungsmodell, Priorisierung im Portfolio anhand der Höhe des IRR – Input für RBAM, Langfristplanung zur Mittelbeschaffung, Konsistente Priorisierung des Projektprogramms
- IREB:RequirementType: Funktion
- SpecIF:Priority: 1_hoch
- dcterms:modified: 2020-06-09T22:00:00.000Z
- dcterms:creator: Bettina Brückner

## REQ_PortfolioMgmt_27 - 'Titel' (IREB:Requirement)
- dcterms:identifier: REQ_PortfolioMgmt_27
- dcterms:subject: PSID 138
- dcterms:description: PSID 138: Prognosekosten Projekt aktuell, Kostenarten, Jahresscheiben, Monat
- IREB:RequirementType: Funktion
- SpecIF:Priority: 1_hoch
- dcterms:modified: 2020-06-09T22:00:00.000Z
- dcterms:creator: Nicole Hentschel, Anne Ebelt

## REQ_PortfolioMgmt_28 - 'Titel' (IREB:Requirement)
- dcterms:identifier: REQ_PortfolioMgmt_28
- dcterms:subject: PSID 139
- dcterms:description: PSID 139: Ist-Kosten Projekt (EL, MuF) Projekt aktuell, Kostenarten, Jahresscheiben, Monat
- IREB:RequirementType: Funktion
- SpecIF:Priority: 1_hoch
- dcterms:modified: 2020-06-09T22:00:00.000Z
- dcterms:creator: Nicole Hentschel, Anne Ebelt

## REQ_PortfolioMgmt_29 - 'Titel' (IREB:Requirement)
- dcterms:identifier: REQ_PortfolioMgmt_29
- dcterms:description: Bereichssteuerung; Prozess Realisierung PLAN/IST (Obligo)/PROGNOSE lt. Kalkulationsschema; Invest/Aufwand; Geschäftsbereiche, Tätigkeitsfelder, monatsscharf, Jahresscheiben
- IREB:RequirementType: Funktion
- SpecIF:Priority: 1_hoch
- dcterms:modified: 2020-06-09T22:00:00.000Z
- dcterms:creator: Nicole Hentschel

## REQ_PortfolioMgmt_30 - 'Titel' (IREB:Requirement)
- dcterms:identifier: REQ_PortfolioMgmt_30
- dcterms:description: IST-/PLAN-Mengen
  Unterscheidung Aufwand/Invest (Ersatz/Erweiterung), Tätigkeitsfelder
- IREB:RequirementType: Funktion
- SpecIF:Priority: 1_hoch
- dcterms:modified: 2020-06-09T22:00:00.000Z
- dcterms:creator: Nicole Hentschel, Anne Ebelt

## REQ_PortfolioMgmt_31 - 'Titel' (IREB:Requirement)
- dcterms:identifier: REQ_PortfolioMgmt_31
- dcterms:description: Plankosten Projekt aktuell, Kostenarten, Jahresscheiben, Monat
- IREB:RequirementType: Funktion
- SpecIF:Priority: 1_hoch
- dcterms:modified: 2020-06-09T22:00:00.000Z
- dcterms:creator: Nicole Hentschel, Anne Ebelt

## REQ_PortfolioMgmt_32 - 'Titel' (IREB:Requirement)
- dcterms:identifier: REQ_PortfolioMgmt_32
- dcterms:description: Prognoseplausibilisierung (kein Eingriff in die Prognose): Verfügt + voraussichtliches Restjahr
- IREB:RequirementType: Funktion
- SpecIF:Priority: 1_hoch
- dcterms:modified: 2020-06-09T22:00:00.000Z
- dcterms:creator: Andre Minke

## REQ_PortfolioMgmt_33 - 'Titel' (IREB:Requirement)
- dcterms:identifier: REQ_PortfolioMgmt_33
- dcterms:subject: PSID 177
- dcterms:description: PSID 177: Einsicht von Schwellwert, monatl.. Ist/Plan-Abweichungsanalyse (inkl. Begründungen) und Quartalsweise Prognose/ Plan Abweichungsbegründungen
- IREB:RequirementType: Funktion
- SpecIF:Priority: 1_hoch
- dcterms:modified: 2020-06-09T22:00:00.000Z
- dcterms:creator: Nicole Hentschel

## REQ_PortfolioMgmt_34 - 'Titel' (IREB:Requirement)
- dcterms:identifier: REQ_PortfolioMgmt_34
- dcterms:subject: PSID 24
- dcterms:description: PSID 42: Extrahierung unterschiedlicher Datenstände zu jedem Zeitpunkt
- IREB:RequirementType: Funktion
- SpecIF:Priority: 1_hoch
- dcterms:modified: 2020-06-09T22:00:00.000Z
- dcterms:creator: Christian Küfner, Nicole Hentschel

## REQ_PortfolioMgmt_35 - 'Titel' (IREB:Requirement)
- dcterms:identifier: REQ_PortfolioMgmt_35
- dcterms:description: Für kaufmännische Steuerungsgrößen, z.B. Prognose
- IREB:RequirementType: Funktion
- SpecIF:Priority: 1_hoch
- dcterms:modified: 2020-06-09T22:00:00.000Z
- dcterms:creator: Christian Küfner, Nicole Hentschel

## REQ_PortfolioMgmt_36- 'Titel' (IREB:Requirement)
- dcterms:identifier: REQ_PortfolioMgmt_36
- dcterms:description: Prognose: Q1, Q2, Q3+ (Projektebene)
  Planung: Entwurfsplanung, Ursprungsplanung, Gen. Budget, Jahresplanung (Projektebene)
- IREB:RequirementType: Funktion
- SpecIF:Priority: 1_hoch
- dcterms:modified: 2020-06-09T22:00:00.000Z
- dcterms:creator: Christian Küfner, Nicole Hentschel

## REQ_PortfolioMgmt_37 - 'Titel' (IREB:Requirement)
- dcterms:identifier: REQ_PortfolioMgmt_37
- dcterms:description: IST- / SOLL Abgleich muss ermöglicht werden
  Datenbestände und Projektstatus beachten!
- IREB:RequirementType: Funktion
- SpecIF:Priority: 1_hoch
- dcterms:modified: 2020-06-09T22:00:00.000Z
- dcterms:creator: Christian Küfner

## REQ_PortfolioMgmt_38 - 'Titel' (IREB:Requirement)
- dcterms:identifier: REQ_PortfolioMgmt_38
- dcterms:subject: PSID 111
- dcterms:description: PSID 111: Parameter WiRe mit Daten Grobplanung speisen, benötigter Detailgrad: Jahresscheiben, BM-Ebene, Finanzraten für Opex und Capex für IFRS und HGB;
- IREB:RequirementType: Funktion
- SpecIF:Priority: 1_hoch
- dcterms:modified: 2020-06-09T22:00:00.000Z
- dcterms:creator: Bettina Brückner, Christian Küfner

## REQ_PortfolioMgmt_39 - 'Titel' (IREB:Requirement)
- dcterms:identifier: REQ_PortfolioMgmt_39
- dcterms:subject: PSID 43 b
- dcterms:description: PSID 43 b: WiRe, Nachweis der Wirtschaftlichkeit im aktuell gültigen Regulierungsmodell, Priorisierung im Portfolio anhand der Höhe des IRR – Input für RBAM, Langfristplanung zur Mittelbeschaffung, Konsistente Priorisierung des Projektprogramms
- IREB:RequirementType: Funktion
- SpecIF:Priority: 1_hoch
- dcterms:modified: 2020-06-09T22:00:00.000Z
- dcterms:creator: Bettina Brückner, Christian Küfner

## REQ_PortfolioMgmt_40 - 'Titel' (IREB:Requirement)
- dcterms:identifier: REQ_PortfolioMgmt_40
- dcterms:subject: PSID 111a
- dcterms:description: PSID 111a: Parameter WiRe mit Daten Grobplanung speisen - > genaue Indikation wirtschaftliche Beurteilung Einzelprojektprogramm auf Basis IRR und NPV, Detailgrad: CAPEX/OPEX, alle Jahresscheiben/Finanzraten, BMG-Ebene, Erlöse/Zuschüsse,  Neubau und Demontage etc
- IREB:RequirementType: Funktion
- SpecIF:Priority: 1_hoch
- dcterms:modified: 2020-06-09T22:00:00.000Z
- dcterms:creator: Bettina Brückner, Christian Küfner

## REQ_PortfolioMgmt_41 - 'Titel' (IREB:Requirement)
- dcterms:identifier: REQ_PortfolioMgmt_41
- dcterms:subject: PSID 62
- dcterms:description: PSID 62: Projektstatus entsprechend Phase (z.B. beauftragt: ja)
- IREB:RequirementType: Funktion
- SpecIF:Priority: 1_hoch
- dcterms:modified: 2020-06-09T22:00:00.000Z
- dcterms:creator: Christian Küfner

## REQ_PortfolioMgmt_42 - 'Titel' (IREB:Requirement)
- dcterms:identifier: REQ_PortfolioMgmt_42
- dcterms:description: Typical/Kalkulation, Initialisierung, Entwurfsplanung, Angebot, Beantragt, Genehmigt, Investitionsentscheidung, Beauftragt, Technisch fertig, Aktiviert, Kfm. Abgeschlossen
- IREB:RequirementType: Funktion
- SpecIF:Priority: 1_hoch
- dcterms:modified: 2020-06-09T22:00:00.000Z
- dcterms:creator: Christian Küfner

## Geschäftsprozesse (SpecIF:Heading)
- dcterms:type: SpecIF:BusinessProcesses

## Modellelemente (Glossar) (SpecIF:Heading)
- dcterms:type: SpecIF:Glossary

## Akteure (SpecIF:Heading)

## Zustände (SpecIF:Heading)

## Ereignisse (SpecIF:Heading)

## Kollektionen und Gruppen (SpecIF:Heading)

## User-Stories (SpecIF:Outline)

## Anforderungen (SpecIF:Outline)

## Modellelemente (Glossar) (SpecIF:Heading)
- dcterms:type: SpecIF:Glossary

## Akteure (SpecIF:Heading)

## Zustände (SpecIF:Heading)

## Ereignisse (SpecIF:Heading)

## Kollektionen und Gruppen (SpecIF:Heading)

## Modellelemente (Glossar) (SpecIF:Heading)
- dcterms:type: SpecIF:Glossary

## Akteure (SpecIF:Heading)

## Zustände (SpecIF:Heading)

## Ereignisse (SpecIF:Heading)

## Kollektionen und Gruppen (SpecIF:Heading)

## Modellelemente (Glossar) (SpecIF:Heading)
- dcterms:type: SpecIF:Glossary

## Akteure (SpecIF:Heading)

## Zustände (SpecIF:Heading)

## Ereignisse (SpecIF:Heading)

## Kollektionen und Gruppen (SpecIF:Heading)

## Modellelemente (Glossar) (SpecIF:Heading)
- dcterms:type: SpecIF:Glossary

## Akteure (SpecIF:Heading)

## Zustände (SpecIF:Heading)

## Ereignisse (SpecIF:Heading)

## Kollektionen und Gruppen (SpecIF:Heading)

## Modellelemente (Glossar) (SpecIF:Heading)
- dcterms:type: SpecIF:Glossary

## Akteure (SpecIF:Heading)

## Zustände (SpecIF:Heading)

## Ereignisse (SpecIF:Heading)

## Kollektionen und Gruppen (SpecIF:Heading)

## Einzelprojekt Hochspannung (SpecIF:Heading)

## Sammelprojekt Mittel-/Niederspannung (SpecIF:Heading)

## Anforderungen (SpecIF:Heading)

## Model-Elements (Glossary) (SpecIF:Heading)
- dcterms:type: SpecIF:Glossary

## Actors (SpecIF:Heading)

## States (SpecIF:Heading)

## Events (SpecIF:Heading)

## Collections and Groups (SpecIF:Heading)

## User-Stories (SpecIF:Heading)

## Model-Elements (Glossary) (SpecIF:Heading)
- dcterms:type: SpecIF:Glossary

## Actors (SpecIF:Heading)

## States (SpecIF:Heading)

## Events (SpecIF:Heading)

## Collections and Groups (SpecIF:Heading)

## Statements
- Organigramm SNB SpecIF:shows Asset Management (DG-AM)
- Organigramm SNB SpecIF:shows Asset Owner Strategy & Business Develop. (DG-DA)
- Organigramm SNB SpecIF:shows Assets (DG-A)
- Organigramm SNB SpecIF:shows Berlin Licht Management (DG-AL)
- Organigramm SNB SpecIF:shows BU Distribution Germany (DG)
- Organigramm SNB SpecIF:shows Business & Project Controlling (DG-CC)
- Organigramm SNB SpecIF:shows Business Administration (DG-CB)
- Organigramm SNB SpecIF:shows Business Control (DG-C)
- Organigramm SNB SpecIF:shows Claim Settlement (DG-CS)
- Organigramm SNB SpecIF:shows Customer & Market Relations (DG-R)
- Organigramm SNB SpecIF:shows Customer Management (DG-RR)
- Organigramm SNB SpecIF:shows Division Management (DG-LM)
- Organigramm SNB SpecIF:shows Field Service Metering (DG-MM)
- Organigramm SNB SpecIF:shows Grid Operation (DG-AG)
- Organigramm SNB SpecIF:shows High Voltage (DG-V)
- Organigramm SNB SpecIF:shows High Voltage Plant Construction (DG-VV)
- Organigramm SNB SpecIF:shows HR & Management Systems (DG-H)
- Organigramm SNB SpecIF:shows HSSE & Management Systems (DG-HS)
- Organigramm SNB SpecIF:shows IT & Data Management (DG-DI)
- Organigramm SNB SpecIF:shows Management Board Coordination (DG-DK)
- Organigramm SNB SpecIF:shows Market Partner Service (DG-RP)
- Organigramm SNB SpecIF:shows Medium & Low Voltage (DG-L)
- Organigramm SNB SpecIF:shows Metering (DG-M)
- Organigramm SNB SpecIF:shows Net Construction (DG-LP)
- Organigramm SNB SpecIF:shows Net Operation MV/ LV (DG-LI)
- Organigramm SNB SpecIF:shows Operations & Project Steering HC (DG-VO)
- Organigramm SNB SpecIF:shows Operations & Project Steering Metering (DG-MS)
- Organigramm SNB SpecIF:shows Operations Management (DG-AO)
- Organigramm SNB SpecIF:shows Operations Metering (DG-MB)
- Organigramm SNB SpecIF:shows Operations Primary Technology (DG-VP)
- Organigramm SNB SpecIF:shows Operations Secondary Technology (DG-VS)
- Organigramm SNB SpecIF:shows Regulatory Management (DG-DR)
- Organigramm SNB SpecIF:shows Regulatory Mgmt./ Strategy Dev./MD SNB (DG-D)
- Organigramm SNB SpecIF:shows Roll out (DG-MR)
- Organigramm SNB SpecIF:shows Stakeholder Management & Communication (DG-RM)
- Organigramm SNB SpecIF:shows Technology Metering (DG-MT)
- SNAP Applikations-Landkarte (Vorlage SNB) SpecIF:shows Ausführung
- SNAP Applikations-Landkarte (Vorlage SNB) SpecIF:shows Beauftr. Ü.
- SNAP Applikations-Landkarte (Vorlage SNB) SpecIF:shows Cal.pro
- SNAP Applikations-Landkarte (Vorlage SNB) SpecIF:shows CaSuP
- SNAP Applikations-Landkarte (Vorlage SNB) SpecIF:shows CosyNet
- SNAP Applikations-Landkarte (Vorlage SNB) SpecIF:shows GM
- SNAP Applikations-Landkarte (Vorlage SNB) SpecIF:shows HAM
- SNAP Applikations-Landkarte (Vorlage SNB) SpecIF:shows Kalk.-Blatt
- SNAP Applikations-Landkarte (Vorlage SNB) SpecIF:shows Kalkulation (EIN.AVA)
- SNAP Applikations-Landkarte (Vorlage SNB) SpecIF:shows NIP
- SNAP Applikations-Landkarte (Vorlage SNB) SpecIF:shows OPAL
- SNAP Applikations-Landkarte (Vorlage SNB) SpecIF:shows PlaNet
- SNAP Applikations-Landkarte (Vorlage SNB) SpecIF:shows Planung
- SNAP Applikations-Landkarte (Vorlage SNB) SpecIF:shows PlanVest
- SNAP Applikations-Landkarte (Vorlage SNB) SpecIF:shows PLC
- SNAP Applikations-Landkarte (Vorlage SNB) SpecIF:shows Prognose
- SNAP Applikations-Landkarte (Vorlage SNB) SpecIF:shows Projektstrukturplan/PAM
- SNAP Applikations-Landkarte (Vorlage SNB) SpecIF:shows PUB
- SNAP Applikations-Landkarte (Vorlage SNB) SpecIF:shows Reporting
- SNAP Applikations-Landkarte (Vorlage SNB) SpecIF:shows SAP
- SNAP Applikations-Landkarte (Vorlage SNB) SpecIF:shows SAP (NeMo)
- SNAP Applikations-Landkarte (Vorlage SNB) SpecIF:shows SNAP
- Applikations-Landkarte SpecIF:shows ADMS
- Applikations-Landkarte SpecIF:shows Alkis
- Applikations-Landkarte SpecIF:shows AutoCAD
- Applikations-Landkarte SpecIF:shows AVA
- Applikations-Landkarte SpecIF:shows Dienstleister-Portal
- Applikations-Landkarte SpecIF:shows DMS
- Applikations-Landkarte SpecIF:shows ECM (Doxis)
- Applikations-Landkarte SpecIF:shows EP_EV_HS
- Applikations-Landkarte SpecIF:shows Felix
- Applikations-Landkarte SpecIF:shows FFM
- Applikations-Landkarte SpecIF:shows HAM
- Applikations-Landkarte SpecIF:shows infreSt
- Applikations-Landkarte SpecIF:shows Ledan
- Applikations-Landkarte SpecIF:shows LiveLink
- Applikations-Landkarte SpecIF:shows MS Project
- Applikations-Landkarte SpecIF:shows MS Visio
- Applikations-Landkarte SpecIF:shows NIS
- Applikations-Landkarte SpecIF:shows NKT XRM
- Applikations-Landkarte SpecIF:shows Projektstrukturplan/PAM
- Applikations-Landkarte SpecIF:shows Sachdaten-Portal
- Applikations-Landkarte SpecIF:shows SAP
- Applikations-Landkarte SpecIF:shows SAP (BANF)
- Applikations-Landkarte SpecIF:shows SAP (NeMo)
- Applikations-Landkarte SpecIF:shows SAP PID
- Applikations-Landkarte SpecIF:shows SAP PS
- Applikations-Landkarte SpecIF:shows SAPCON
- Applikations-Landkarte SpecIF:shows SP_KV_MSNS
- AVA-Applikationen (IST) SpecIF:shows BauSU
- AVA-Applikationen (IST) SpecIF:shows California.pro
- AVA-Applikationen (IST) SpecIF:shows Dienstleister-Portal
- AVA-Applikationen (IST) SpecIF:shows Felix
- AVA-Applikationen (IST) SpecIF:shows iTWO
- AVA-Applikationen (IST) SpecIF:shows Preis-DB
- AVA-Applikationen (IST) SpecIF:shows SAP
- AVA-Applikationen (IST) SpecIF:shows SAP (NeMo)
- AVA-Applikationen (IST) SpecIF:shows SAP Ariba
- AVA-Applikation (Referenz) SpecIF:shows Abrechnung
- AVA-Applikation (Referenz) SpecIF:shows Abrechnungs-Daten (GAEB)
- AVA-Applikation (Referenz) SpecIF:shows Angebots-Daten (GAEB)
- AVA-Applikation (Referenz) SpecIF:shows Angebots-Erstellung
- AVA-Applikation (Referenz) SpecIF:shows Ausschreibung
- AVA-Applikation (Referenz) SpecIF:shows AVA
- AVA-Applikation (Referenz) SpecIF:shows Bauunternehmen
- AVA-Applikation (Referenz) SpecIF:shows CAD Hoch/Tiefbau
- AVA-Applikation (Referenz) SpecIF:shows ERP
- AVA-Applikation (Referenz) SpecIF:shows Finanzdaten
- AVA-Applikation (Referenz) SpecIF:shows Leistungs-Verzeichnis (GAEB)
- AVA-Applikation (Referenz) SpecIF:shows NIS
- AVA-Applikation (Referenz) SpecIF:shows Raumdaten Bau
- AVA-Applikation (Referenz) SpecIF:shows Rechnungs-Erstellung
- AVA-Applikation (Referenz) SpecIF:shows Umgebungsdaten
- AVA-Applikation (Referenz) SpecIF:shows Vergabe
- Applikations-Landkarte (Interaction Room - zu klären) SpecIF:shows BauSU
- Applikations-Landkarte (Interaction Room - zu klären) SpecIF:shows Diagnose-Tool MS-Kabel
- Applikations-Landkarte (Interaction Room - zu klären) SpecIF:shows eBASE
- Applikations-Landkarte (Interaction Room - zu klären) SpecIF:shows Geräte-Management
- Applikations-Landkarte (Interaction Room - zu klären) SpecIF:shows iTWO
- Applikations-Landkarte (Interaction Room - zu klären) SpecIF:shows Kalkulations-Tool
- Applikations-Landkarte (Interaction Room - zu klären) SpecIF:shows Ledan
- Applikations-Landkarte (Interaction Room - zu klären) SpecIF:shows MoNIS
- Applikations-Landkarte (Interaction Room - zu klären) SpecIF:shows NIP
- Applikations-Landkarte (Interaction Room - zu klären) SpecIF:shows OPAL
- Applikations-Landkarte (Interaction Room - zu klären) SpecIF:shows PlanVest
- Applikations-Landkarte (Interaction Room - zu klären) SpecIF:shows PowerWork Zähleranschluss-App
- Applikations-Landkarte (Interaction Room - zu klären) SpecIF:shows ProKoLi
- Applikations-Landkarte (Interaction Room - zu klären) SpecIF:shows SAP PM
- EP_EV_HS_Fachobjekte SpecIF:shows Abnahmeprotokoll
- EP_EV_HS_Fachobjekte SpecIF:shows Abstimmungsprotokoll [AM]
- EP_EV_HS_Fachobjekte SpecIF:shows Ausschreibungsunterlagen
- EP_EV_HS_Fachobjekte SpecIF:shows Baustellendokumentation
- EP_EV_HS_Fachobjekte SpecIF:shows Baustellendokumentation [erstellt]
- EP_EV_HS_Fachobjekte SpecIF:shows Baustellendokumentation [kommentiert]
- EP_EV_HS_Fachobjekte SpecIF:shows Betriebsmitteldaten
- EP_EV_HS_Fachobjekte SpecIF:shows Eckterminplan [inkl. Beschaffungsprozess]
- EP_EV_HS_Fachobjekte SpecIF:shows Enddokumentation
- EP_EV_HS_Fachobjekte SpecIF:shows Entscheidungsvorlage je Variante (Projektsteckbrief)
- EP_EV_HS_Fachobjekte SpecIF:shows EP_EV_HS
- EP_EV_HS_Fachobjekte SpecIF:shows Gesamtkapazitätsplanung je Gruppe
- EP_EV_HS_Fachobjekte SpecIF:shows Gesamtkapazitätsplanung Unternehmen
- EP_EV_HS_Fachobjekte SpecIF:shows Grobterminplan
- EP_EV_HS_Fachobjekte SpecIF:shows Langfristplanung
- EP_EV_HS_Fachobjekte SpecIF:shows Leistungsbestätigungs-Dokumente
- EP_EV_HS_Fachobjekte SpecIF:shows NPK Protokoll
- EP_EV_HS_Fachobjekte SpecIF:shows NPK Präsentation
- EP_EV_HS_Fachobjekte SpecIF:shows Organigramm
- EP_EV_HS_Fachobjekte SpecIF:shows Projektakte
- EP_EV_HS_Fachobjekte SpecIF:shows Projektakte - Dokumentation
- EP_EV_HS_Fachobjekte SpecIF:shows Projektakte - Dokumentation [Review]
- EP_EV_HS_Fachobjekte SpecIF:shows Projektakte - Entwurfsplanung
- EP_EV_HS_Fachobjekte SpecIF:shows Projektakte - Feinplanung
- EP_EV_HS_Fachobjekte SpecIF:shows Projektakte - Feinplanung [Bauführer]
- EP_EV_HS_Fachobjekte SpecIF:shows Projektakte - Feinplanung [final]
- EP_EV_HS_Fachobjekte SpecIF:shows Projektakte - Feinplanung [nach Bestellung]
- EP_EV_HS_Fachobjekte SpecIF:shows Projektakte - PL-Entwurfsplanung
- EP_EV_HS_Fachobjekte SpecIF:shows Projektakte - Projektstudie
- EP_EV_HS_Fachobjekte SpecIF:shows Projektakte - Projektstudie [beauftragt]
- EP_EV_HS_Fachobjekte SpecIF:shows Projektakte - Projektstudie [entworfen]
- EP_EV_HS_Fachobjekte SpecIF:shows Projektakte - Projektstudie [konzipiert]
- EP_EV_HS_Fachobjekte SpecIF:shows Projektakte - Projektstudie [PlausiAS]
- EP_EV_HS_Fachobjekte SpecIF:shows Projektakte - TP-Entwurfsplanung
- EP_EV_HS_Fachobjekte SpecIF:shows Projektakte - TP-Genehmigungsplanung
- EP_EV_HS_Fachobjekte SpecIF:shows Projektakte - TP-Grobplanung
- EP_EV_HS_Fachobjekte SpecIF:shows Projektakte [empfohl. Variante_FINAL]
- EP_EV_HS_Fachobjekte SpecIF:shows Projektakte [Kostenschätzung]
- EP_EV_HS_Fachobjekte SpecIF:shows Projektakte [PlanungsrechtKlar]
- EP_EV_HS_Fachobjekte SpecIF:shows Projektakte [RBAM/WiRe]
- EP_EV_HS_Fachobjekte SpecIF:shows Projektakte [techn. Lösung]
- EP_EV_HS_Fachobjekte SpecIF:shows Projektakte [techn. Lösung_Typicals]
- EP_EV_HS_Fachobjekte SpecIF:shows Projektakte [Variante_NPK1]
- EP_EV_HS_Fachobjekte SpecIF:shows Projektakte [Varianten]
- EP_EV_HS_Fachobjekte SpecIF:shows Projektannahme-Empfehlung
- EP_EV_HS_Fachobjekte SpecIF:shows Projektannahme-Empfehlung [freigegeben]
- EP_EV_HS_Fachobjekte SpecIF:shows Projektannahme-Empfehlung [zur Freigabe]
- EP_EV_HS_Fachobjekte SpecIF:shows Projektimpuls
- EP_EV_HS_Fachobjekte SpecIF:shows Projektimpuls [Kat+Typ]
- EP_EV_HS_Fachobjekte SpecIF:shows Projektmittelantrag
- EP_EV_HS_Fachobjekte SpecIF:shows Projektsteckbrief PL
- EP_EV_HS_Fachobjekte SpecIF:shows Projektübersichts-Liste
- EP_EV_HS_Fachobjekte SpecIF:shows Protokoll Baubesprechung
- EP_EV_HS_Fachobjekte SpecIF:shows Protokoll Projektmittelantragsprüfung
- EP_EV_HS_Fachobjekte SpecIF:shows PSP Elemente Planung
- EP_EV_HS_Fachobjekte SpecIF:shows Restpunktliste
- EP_EV_HS_Fachobjekte SpecIF:shows Standardzahlplan
- EP_EV_HS_Fachobjekte SpecIF:shows Technische Fertigmeldung
- EP_EV_HS_Fachobjekte SpecIF:shows Vergabeentscheidung
- EP_EV_HS_Fachobjekte SpecIF:shows Vertrag Auftragnehmer (AN)
- EP_EV_HS_Fachobjekte SpecIF:shows Werksprüfungsprotokoll
- EP_EV_HS_Fachobjekte SpecIF:shows Zahlplan [Entwurf]
- EP_EV_HS_Fachobjekte SpecIF:shows Zahlplan [individuell für jede VE]
- SP_KV_MSNS_Fachobjekte SpecIF:shows Ausführungsplan
- SP_KV_MSNS_Fachobjekte SpecIF:shows Ausführungsplan [erweitert]
- SP_KV_MSNS_Fachobjekte SpecIF:shows Ausführungsplan [initial]
- SP_KV_MSNS_Fachobjekte SpecIF:shows Ausschreibungsunterlagen
- SP_KV_MSNS_Fachobjekte SpecIF:shows Bauakte
- SP_KV_MSNS_Fachobjekte SpecIF:shows Bauakte [abgeschlossen]
- SP_KV_MSNS_Fachobjekte SpecIF:shows Bauakte [angenommen]
- SP_KV_MSNS_Fachobjekte SpecIF:shows Bauakte [bemängelt]
- SP_KV_MSNS_Fachobjekte SpecIF:shows Bauakte [final_geprüft]
- SP_KV_MSNS_Fachobjekte SpecIF:shows Baufreigabe
- SP_KV_MSNS_Fachobjekte SpecIF:shows Beauftragung Kunde
- SP_KV_MSNS_Fachobjekte SpecIF:shows Budgetentscheidung
- SP_KV_MSNS_Fachobjekte SpecIF:shows Budgetforderung
- SP_KV_MSNS_Fachobjekte SpecIF:shows Genehmigungen/Leitungsauskünfte
- SP_KV_MSNS_Fachobjekte SpecIF:shows Genehmigungsplan
- SP_KV_MSNS_Fachobjekte SpecIF:shows Kundenanfrage
- SP_KV_MSNS_Fachobjekte SpecIF:shows Kundenanfrage [bewertet Berater]
- SP_KV_MSNS_Fachobjekte SpecIF:shows Kundenanfrage [bewertet Konzeption]
- SP_KV_MSNS_Fachobjekte SpecIF:shows Kundenanfrage [initial]
- SP_KV_MSNS_Fachobjekte SpecIF:shows Kundenanfrage [technisch geprüft]
- SP_KV_MSNS_Fachobjekte SpecIF:shows Kundenangebot
- SP_KV_MSNS_Fachobjekte SpecIF:shows Leistungserfassungsblatt
- SP_KV_MSNS_Fachobjekte SpecIF:shows Leistungserfassungsblatt [bestätigt]
- SP_KV_MSNS_Fachobjekte SpecIF:shows Maßnahmenempfehlungs-Liste
- SP_KV_MSNS_Fachobjekte SpecIF:shows Montageauftrag [erteilt]
- SP_KV_MSNS_Fachobjekte SpecIF:shows Netzbauauftrag
- SP_KV_MSNS_Fachobjekte SpecIF:shows SP_KV_MSNS
- SP_KV_MSNS_Fachobjekte SpecIF:shows Stationsbauauftrag
- SP_KV_MSNS_Fachobjekte SpecIF:shows Stationszeichnung
- SP_KV_MSNS_Fachobjekte SpecIF:shows Technisches Konzept
- SP_KV_MSNS_Fachobjekte SpecIF:shows Technisches Konzept [bemängelt]
- SP_KV_MSNS_Fachobjekte SpecIF:shows Technisches Konzept [erstellt]
- SP_KV_MSNS_Fachobjekte SpecIF:shows Technisches Konzept [final konzipiert]
- SP_KV_MSNS_Fachobjekte SpecIF:shows Technisches Konzept [geprüft]
- SP_KV_MSNS_Fachobjekte SpecIF:shows Technisches Konzept [HA final konzipiert]
- SP_KV_MSNS_Fachobjekte SpecIF:shows Technisches Konzept [kalkuliert]
- SP_KV_MSNS_Fachobjekte SpecIF:shows Technisches Konzept [SKB final konzipiert]
- SP_KV_MSNS_Fachobjekte SpecIF:shows Vertrag/Verträge mit AN
- Abrechnung SpecIF:writes Finanzdaten
- Abrechnung SpecIF:reads Abrechnungs-Daten (GAEB)
- Angebots-Erstellung SpecIF:writes Angebots-Daten (GAEB)
- Angebots-Erstellung SpecIF:reads Leistungs-Verzeichnis (GAEB)
- Assets (DG-A) SpecIF:contains Asset Management (DG-AM)
- Assets (DG-A) SpecIF:contains Berlin Licht Management (DG-AL)
- Assets (DG-A) SpecIF:contains Grid Operation (DG-AG)
- Assets (DG-A) SpecIF:contains Operations Management (DG-AO)
- Ausführung SpecIF:contains Kalk.-Blatt
- Ausführung SpecIF:contains OPAL
- Ausführungsplan [erweitert] SpecIF:contains Ausführungsplan
- Ausführungsplan [initial] SpecIF:contains Ausführungsplan
- Ausschreibung SpecIF:writes Leistungs-Verzeichnis (GAEB)
- Ausschreibung SpecIF:reads Raumdaten Bau
- AVA SpecIF:contains Abrechnung
- AVA SpecIF:contains Ausschreibung
- AVA SpecIF:contains Vergabe
- Bauakte [abgeschlossen] SpecIF:contains Bauakte
- Bauakte [angenommen] SpecIF:contains Bauakte
- Bauakte [bemängelt] SpecIF:contains Bauakte
- Bauakte [final_geprüft] SpecIF:contains Bauakte
- Baustellendokumentation [erstellt] SpecIF:contains Baustellendokumentation
- Baustellendokumentation [kommentiert] SpecIF:contains Baustellendokumentation
- Bauunternehmen SpecIF:contains Angebots-Erstellung
- Bauunternehmen SpecIF:contains Rechnungs-Erstellung
- BU Distribution Germany (DG) SpecIF:contains Assets (DG-A)
- BU Distribution Germany (DG) SpecIF:contains Business Control (DG-C)
- BU Distribution Germany (DG) SpecIF:contains Customer & Market Relations (DG-R)
- BU Distribution Germany (DG) SpecIF:contains High Voltage (DG-V)
- BU Distribution Germany (DG) SpecIF:contains HR & Management Systems (DG-H)
- BU Distribution Germany (DG) SpecIF:contains Medium & Low Voltage (DG-L)
- BU Distribution Germany (DG) SpecIF:contains Metering (DG-M)
- BU Distribution Germany (DG) SpecIF:contains Regulatory Mgmt./ Strategy Dev./MD SNB (DG-D)
- Business Control (DG-C) SpecIF:contains Business & Project Controlling (DG-CC)
- Business Control (DG-C) SpecIF:contains Business Administration (DG-CB)
- Business Control (DG-C) SpecIF:contains Claim Settlement (DG-CS)
- CAD Hoch/Tiefbau SpecIF:writes Umgebungsdaten
- CAD Hoch/Tiefbau SpecIF:reads Umgebungsdaten
- CAD Hoch/Tiefbau SpecIF:writes Raumdaten Bau
- Customer & Market Relations (DG-R) SpecIF:contains Customer Management (DG-RR)
- Customer & Market Relations (DG-R) SpecIF:contains Market Partner Service (DG-RP)
- Customer & Market Relations (DG-R) SpecIF:contains Stakeholder Management & Communication (DG-RM)
- EP_EV_HS SpecIF:contains AVA
- EP_EV_HS SpecIF:contains DMS
- EP_EV_HS SpecIF:contains FFM
- EP_EV_HS SpecIF:contains MS Project
- EP_EV_HS SpecIF:contains Projektstrukturplan/PAM
- EP_EV_HS SpecIF:contains SAP
- EP_EV_HS SpecIF:contains SAP (BANF)
- EP_EV_HS SpecIF:contains SAP PID
- EP_EV_HS SpecIF:contains SAP PS
- EP_EV_HS SpecIF:contains SAPCON
- EP_EV_HS SpecIF:contains Abnahmeprotokoll
- EP_EV_HS SpecIF:contains Abstimmungsprotokoll [AM]
- EP_EV_HS SpecIF:contains Ausschreibungsunterlagen
- EP_EV_HS SpecIF:contains Baustellendokumentation
- EP_EV_HS SpecIF:contains Baustellendokumentation [erstellt]
- EP_EV_HS SpecIF:contains Baustellendokumentation [kommentiert]
- EP_EV_HS SpecIF:contains Betriebsmitteldaten
- EP_EV_HS SpecIF:contains Eckterminplan [inkl. Beschaffungsprozess]
- EP_EV_HS SpecIF:contains Enddokumentation
- EP_EV_HS SpecIF:contains Entscheidungsvorlage je Variante (Projektsteckbrief)
- EP_EV_HS SpecIF:contains Gesamtkapazitätsplanung je Gruppe
- EP_EV_HS SpecIF:contains Gesamtkapazitätsplanung Unternehmen
- EP_EV_HS SpecIF:contains Grobterminplan
- EP_EV_HS SpecIF:contains Langfristplanung
- EP_EV_HS SpecIF:contains Leistungsbestätigungs-Dokumente
- EP_EV_HS SpecIF:contains NPK Protokoll
- EP_EV_HS SpecIF:contains NPK Präsentation
- EP_EV_HS SpecIF:contains Organigramm
- EP_EV_HS SpecIF:contains Projektakte
- EP_EV_HS SpecIF:contains Projektakte - Dokumentation
- EP_EV_HS SpecIF:contains Projektakte - Dokumentation [Review]
- EP_EV_HS SpecIF:contains Projektakte - Entwurfsplanung
- EP_EV_HS SpecIF:contains Projektakte - Feinplanung
- EP_EV_HS SpecIF:contains Projektakte - Feinplanung [Bauführer]
- EP_EV_HS SpecIF:contains Projektakte - Feinplanung [final]
- EP_EV_HS SpecIF:contains Projektakte - Feinplanung [nach Bestellung]
- EP_EV_HS SpecIF:contains Projektakte - PL-Entwurfsplanung
- EP_EV_HS SpecIF:contains Projektakte - Projektstudie
- EP_EV_HS SpecIF:contains Projektakte - Projektstudie [beauftragt]
- EP_EV_HS SpecIF:contains Projektakte - Projektstudie [entworfen]
- EP_EV_HS SpecIF:contains Projektakte - Projektstudie [konzipiert]
- EP_EV_HS SpecIF:contains Projektakte - Projektstudie [PlausiAS]
- EP_EV_HS SpecIF:contains Projektakte - TP-Entwurfsplanung
- EP_EV_HS SpecIF:contains Projektakte - TP-Genehmigungsplanung
- EP_EV_HS SpecIF:contains Projektakte - TP-Grobplanung
- EP_EV_HS SpecIF:contains Projektakte [empfohl. Variante_FINAL]
- EP_EV_HS SpecIF:contains Projektakte [Kostenschätzung]
- EP_EV_HS SpecIF:contains Projektakte [PlanungsrechtKlar]
- EP_EV_HS SpecIF:contains Projektakte [RBAM/WiRe]
- EP_EV_HS SpecIF:contains Projektakte [techn. Lösung]
- EP_EV_HS SpecIF:contains Projektakte [techn. Lösung_Typicals]
- EP_EV_HS SpecIF:contains Projektakte [Variante_NPK1]
- EP_EV_HS SpecIF:contains Projektakte [Varianten]
- EP_EV_HS SpecIF:contains Projektannahme-Empfehlung
- EP_EV_HS SpecIF:contains Projektannahme-Empfehlung [freigegeben]
- EP_EV_HS SpecIF:contains Projektannahme-Empfehlung [zur Freigabe]
- EP_EV_HS SpecIF:contains Projektimpuls
- EP_EV_HS SpecIF:contains Projektimpuls [Kat+Typ]
- EP_EV_HS SpecIF:contains Projektmittelantrag
- EP_EV_HS SpecIF:contains Projektsteckbrief PL
- EP_EV_HS SpecIF:contains Projektübersichts-Liste
- EP_EV_HS SpecIF:contains Protokoll Baubesprechung
- EP_EV_HS SpecIF:contains Protokoll Projektmittelantragsprüfung
- EP_EV_HS SpecIF:contains PSP Elemente Planung
- EP_EV_HS SpecIF:contains Restpunktliste
- EP_EV_HS SpecIF:contains Standardzahlplan
- EP_EV_HS SpecIF:contains Technische Fertigmeldung
- EP_EV_HS SpecIF:contains Vergabeentscheidung
- EP_EV_HS SpecIF:contains Vertrag Auftragnehmer (AN)
- EP_EV_HS SpecIF:contains Werksprüfungsprotokoll
- EP_EV_HS SpecIF:contains Zahlplan [Entwurf]
- EP_EV_HS SpecIF:contains Zahlplan [individuell für jede VE]
- ERP SpecIF:reads Finanzdaten
- SAP (NeMo) SpecIF:sendsTo Felix
- High Voltage (DG-V) SpecIF:contains High Voltage Plant Construction (DG-VV)
- High Voltage (DG-V) SpecIF:contains Operations & Project Steering HC (DG-VO)
- High Voltage (DG-V) SpecIF:contains Operations Primary Technology (DG-VP)
- High Voltage (DG-V) SpecIF:contains Operations Secondary Technology (DG-VS)
- HR & Management Systems (DG-H) SpecIF:contains HSSE & Management Systems (DG-HS)
- Kalkulation (EIN.AVA) SpecIF:contains Cal.pro
- Kalkulation (EIN.AVA) SpecIF:contains CaSuP
- SNAP SpecIF:sendsTo Kalkulation (EIN.AVA)
- Kundenanfrage [bewertet Berater] SpecIF:contains Kundenanfrage
- Kundenanfrage [bewertet Konzeption] SpecIF:contains Kundenanfrage
- Kundenanfrage [initial] SpecIF:contains Kundenanfrage
- Kundenanfrage [technisch geprüft] SpecIF:contains Kundenanfrage
- Leistungserfassungsblatt [bestätigt] SpecIF:contains Leistungserfassungsblatt
- Medium & Low Voltage (DG-L) SpecIF:contains Division Management (DG-LM)
- Medium & Low Voltage (DG-L) SpecIF:contains Net Construction (DG-LP)
- Medium & Low Voltage (DG-L) SpecIF:contains Net Operation MV/ LV (DG-LI)
- Metering (DG-M) SpecIF:contains Field Service Metering (DG-MM)
- Metering (DG-M) SpecIF:contains Operations & Project Steering Metering (DG-MS)
- Metering (DG-M) SpecIF:contains Operations Metering (DG-MB)
- Metering (DG-M) SpecIF:contains Roll out (DG-MR)
- Metering (DG-M) SpecIF:contains Technology Metering (DG-MT)
- NIS SpecIF:writes Umgebungsdaten
- NIS SpecIF:reads Umgebungsdaten
- Planung SpecIF:contains Beauftr. Ü.
- Planung SpecIF:contains Kalk.-Blatt
- Planung SpecIF:contains PlanVest
- Planung SpecIF:contains Projektstrukturplan/PAM
- Prognose SpecIF:contains PLC
- Prognose SpecIF:contains PUB
- Projektakte SpecIF:contains Abstimmungsprotokoll [AM]
- Projektakte SpecIF:contains Entscheidungsvorlage je Variante (Projektsteckbrief)
- Projektakte SpecIF:contains Gesamtkapazitätsplanung je Gruppe
- Projektakte SpecIF:contains Gesamtkapazitätsplanung Unternehmen
- Projektakte SpecIF:contains NPK Protokoll
- Projektakte SpecIF:contains NPK Präsentation
- Projektakte SpecIF:contains Organigramm
- Projektakte SpecIF:contains Projektakte - Dokumentation
- Projektakte SpecIF:contains Projektakte - Entwurfsplanung
- Projektakte SpecIF:contains Projektakte - Feinplanung
- Projektakte SpecIF:contains Projektakte - Projektstudie
- Projektakte SpecIF:contains Projektannahme-Empfehlung
- Projektakte SpecIF:contains Projektimpuls
- Projektakte SpecIF:contains Projektsteckbrief PL
- Projektakte - Dokumentation SpecIF:contains Abnahmeprotokoll
- Projektakte - Dokumentation SpecIF:contains Enddokumentation
- Projektakte - Dokumentation SpecIF:contains Leistungsbestätigungs-Dokumente
- Projektakte - Dokumentation SpecIF:contains Technische Fertigmeldung
- Projektakte - Dokumentation [Review] SpecIF:contains Projektakte - Dokumentation
- Projektakte - Entwurfsplanung SpecIF:contains Eckterminplan [inkl. Beschaffungsprozess]
- Projektakte - Entwurfsplanung SpecIF:contains Projektakte - TP-Entwurfsplanung
- Projektakte - Entwurfsplanung SpecIF:contains Projektakte - TP-Genehmigungsplanung
- Projektakte - Entwurfsplanung SpecIF:contains Projektakte - TP-Grobplanung
- Projektakte - Entwurfsplanung SpecIF:contains Standardzahlplan
- Projektakte - Feinplanung SpecIF:contains Ausschreibungsunterlagen
- Projektakte - Feinplanung SpecIF:contains Baustellendokumentation
- Projektakte - Feinplanung SpecIF:contains Betriebsmitteldaten
- Projektakte - Feinplanung SpecIF:contains Protokoll Baubesprechung
- Projektakte - Feinplanung SpecIF:contains Restpunktliste
- Projektakte - Feinplanung SpecIF:contains Vergabeentscheidung
- Projektakte - Feinplanung SpecIF:contains Vertrag Auftragnehmer (AN)
- Projektakte - Feinplanung SpecIF:contains Werksprüfungsprotokoll
- Projektakte - Feinplanung [final] SpecIF:contains Projektakte - Feinplanung
- Projektakte - Feinplanung [nach Bestellung] SpecIF:contains Projektakte - Feinplanung
- Projektakte - PL-Entwurfsplanung SpecIF:contains Grobterminplan
- Projektakte - Projektstudie SpecIF:contains Projektmittelantrag
- Projektakte - Projektstudie SpecIF:contains Protokoll Projektmittelantragsprüfung
- Projektakte - Projektstudie SpecIF:contains PSP Elemente Planung
- Projektakte - Projektstudie [beauftragt] SpecIF:contains Projektakte - Projektstudie
- Projektakte - Projektstudie [entworfen] SpecIF:contains Projektakte - Projektstudie
- Projektakte - Projektstudie [konzipiert] SpecIF:contains Projektakte - Projektstudie
- Projektakte - Projektstudie [PlausiAS] SpecIF:contains Projektakte - Projektstudie
- Projektakte [empfohl. Variante_FINAL] SpecIF:contains Projektakte
- Projektakte [Kostenschätzung] SpecIF:contains Projektakte
- Projektakte [PlanungsrechtKlar] SpecIF:contains Projektakte
- Projektakte [RBAM/WiRe] SpecIF:contains Projektakte
- Projektakte [techn. Lösung] SpecIF:contains Projektakte
- Projektakte [techn. Lösung_Typicals] SpecIF:contains Projektakte
- Projektakte [Variante_NPK1] SpecIF:contains Projektakte
- Projektakte [Varianten] SpecIF:contains Projektakte
- Projektannahme-Empfehlung [freigegeben] SpecIF:contains Projektannahme-Empfehlung
- Projektannahme-Empfehlung [zur Freigabe] SpecIF:contains Projektannahme-Empfehlung
- Projektimpuls [Kat+Typ] SpecIF:contains Projektimpuls
- Rechnungs-Erstellung SpecIF:writes Abrechnungs-Daten (GAEB)
- Rechnungs-Erstellung SpecIF:reads Angebots-Daten (GAEB)
- Regulatory Mgmt./ Strategy Dev./MD SNB (DG-D) SpecIF:contains Asset Owner Strategy & Business Develop. (DG-DA)
- Regulatory Mgmt./ Strategy Dev./MD SNB (DG-D) SpecIF:contains IT & Data Management (DG-DI)
- Regulatory Mgmt./ Strategy Dev./MD SNB (DG-D) SpecIF:contains Management Board Coordination (DG-DK)
- Regulatory Mgmt./ Strategy Dev./MD SNB (DG-D) SpecIF:contains Regulatory Management (DG-DR)
- Reporting SpecIF:contains Beauftr. Ü.
- Reporting SpecIF:contains CosyNet
- Reporting SpecIF:contains Kalk.-Blatt
- Reporting SpecIF:contains NIP
- SAP SpecIF:contains GM
- SAP SpecIF:contains HAM
- SAP SpecIF:contains PlaNet
- SAP SpecIF:contains SAP (NeMo)
- SNAP SpecIF:sendsTo SAP
- Felix SpecIF:sendsTo SAP (NeMo)
- SNAP SpecIF:contains Ausführung
- SNAP SpecIF:contains Planung
- SNAP SpecIF:contains Prognose
- SNAP SpecIF:contains Reporting
- Kalkulation (EIN.AVA) SpecIF:sendsTo SNAP
- SAP SpecIF:sendsTo SNAP
- SP_KV_MSNS SpecIF:contains Ausführungsplan
- SP_KV_MSNS SpecIF:contains Ausführungsplan [erweitert]
- SP_KV_MSNS SpecIF:contains Ausführungsplan [initial]
- SP_KV_MSNS SpecIF:contains Ausschreibungsunterlagen
- SP_KV_MSNS SpecIF:contains Bauakte
- SP_KV_MSNS SpecIF:contains Bauakte [abgeschlossen]
- SP_KV_MSNS SpecIF:contains Bauakte [angenommen]
- SP_KV_MSNS SpecIF:contains Bauakte [bemängelt]
- SP_KV_MSNS SpecIF:contains Bauakte [final_geprüft]
- SP_KV_MSNS SpecIF:contains Baufreigabe
- SP_KV_MSNS SpecIF:contains Beauftragung Kunde
- SP_KV_MSNS SpecIF:contains Budgetentscheidung
- SP_KV_MSNS SpecIF:contains Budgetforderung
- SP_KV_MSNS SpecIF:contains Genehmigungen/Leitungsauskünfte
- SP_KV_MSNS SpecIF:contains Genehmigungsplan
- SP_KV_MSNS SpecIF:contains Kundenanfrage
- SP_KV_MSNS SpecIF:contains Kundenanfrage [bewertet Berater]
- SP_KV_MSNS SpecIF:contains Kundenanfrage [bewertet Konzeption]
- SP_KV_MSNS SpecIF:contains Kundenanfrage [initial]
- SP_KV_MSNS SpecIF:contains Kundenanfrage [technisch geprüft]
- SP_KV_MSNS SpecIF:contains Kundenangebot
- SP_KV_MSNS SpecIF:contains Leistungserfassungsblatt
- SP_KV_MSNS SpecIF:contains Leistungserfassungsblatt [bestätigt]
- SP_KV_MSNS SpecIF:contains Maßnahmenempfehlungs-Liste
- SP_KV_MSNS SpecIF:contains Montageauftrag [erteilt]
- SP_KV_MSNS SpecIF:contains Netzbauauftrag
- SP_KV_MSNS SpecIF:contains Stationsbauauftrag
- SP_KV_MSNS SpecIF:contains Stationszeichnung
- SP_KV_MSNS SpecIF:contains Technisches Konzept
- SP_KV_MSNS SpecIF:contains Technisches Konzept [bemängelt]
- SP_KV_MSNS SpecIF:contains Technisches Konzept [erstellt]
- SP_KV_MSNS SpecIF:contains Technisches Konzept [final konzipiert]
- SP_KV_MSNS SpecIF:contains Technisches Konzept [geprüft]
- SP_KV_MSNS SpecIF:contains Technisches Konzept [HA final konzipiert]
- SP_KV_MSNS SpecIF:contains Technisches Konzept [kalkuliert]
- SP_KV_MSNS SpecIF:contains Technisches Konzept [SKB final konzipiert]
- SP_KV_MSNS SpecIF:contains Vertrag/Verträge mit AN
- SP_KV_MSNS SpecIF:contains ADMS
- SP_KV_MSNS SpecIF:contains Alkis
- SP_KV_MSNS SpecIF:contains AutoCAD
- SP_KV_MSNS SpecIF:contains AVA
- SP_KV_MSNS SpecIF:contains Dienstleister-Portal
- SP_KV_MSNS SpecIF:contains ECM (Doxis)
- SP_KV_MSNS SpecIF:contains Felix
- SP_KV_MSNS SpecIF:contains FFM
- SP_KV_MSNS SpecIF:contains HAM
- SP_KV_MSNS SpecIF:contains infreSt
- SP_KV_MSNS SpecIF:contains Ledan
- SP_KV_MSNS SpecIF:contains LiveLink
- SP_KV_MSNS SpecIF:contains MS Visio
- SP_KV_MSNS SpecIF:contains NIS
- SP_KV_MSNS SpecIF:contains NKT XRM
- SP_KV_MSNS SpecIF:contains Sachdaten-Portal
- SP_KV_MSNS SpecIF:contains SAP
- SP_KV_MSNS SpecIF:contains SAP (BANF)
- SP_KV_MSNS SpecIF:contains SAP (NeMo)
- SP_KV_MSNS SpecIF:contains SAP PS
- Technisches Konzept [bemängelt] SpecIF:contains Technisches Konzept
- Technisches Konzept [erstellt] SpecIF:contains Technisches Konzept
- Technisches Konzept [final konzipiert] SpecIF:contains Technisches Konzept
- Technisches Konzept [geprüft] SpecIF:contains Technisches Konzept
- Technisches Konzept [HA final konzipiert] SpecIF:contains Technisches Konzept
- Technisches Konzept [kalkuliert] SpecIF:contains Technisches Konzept
- Technisches Konzept [SKB final konzipiert] SpecIF:contains Technisches Konzept
- Vergabe SpecIF:reads Angebots-Daten (GAEB)
- Zahlplan [Entwurf] SpecIF:contains Standardzahlplan
- Zahlplan [individuell für jede VE] SpecIF:contains Standardzahlplan
- Einzelprojekt HS SpecIF:contains Asset Management - Konzeption
- Einzelprojekt HS SpecIF:contains Asset Management - Portfoliomanagement
- Einzelprojekt HS SpecIF:contains Asset Service
- 3:Projekt beantragen SpecIF:reads Projektakte - Projektstudie [konzipiert]
- 3:Projekt beantragen SpecIF:reads PSP Elemente Planung
- 3:Projekt beantragen SpecIF:writes Projektakte - Projektstudie [beauftragt]
- 3:Projekt beantragen SpecIF:writes Projektmittelantrag
- Asset Management - Portfoliomanagement SpecIF:contains 3:Projekt beantragen
- Aufnahme des Projektes in die aktive Planung SpecIF:writes Projektimpuls
- Asset Management - Konzeption SpecIF:contains Aufnahme des Projektes in die aktive Planung
- 1:Projekt initialisieren SpecIF:reads Projektimpuls
- 1:Projekt initialisieren SpecIF:reads SNAP
- 1:Projekt initialisieren SpecIF:writes Projektakte [Variante_NPK1]
- 1:Projekt initialisieren SpecIF:writes SNAP
- 1:Projekt initialisieren SpecIF:writes Kalkulation
- Asset Management - Konzeption SpecIF:contains 1:Projekt initialisieren
- 2:Projekt konzipieren SpecIF:reads Projektakte [Variante_NPK1]
- 2:Projekt konzipieren SpecIF:writes PSP Elemente Planung
- 2:Projekt konzipieren SpecIF:writes Projektakte - Projektstudie [konzipiert]
- Asset Management - Konzeption SpecIF:contains 2:Projekt konzipieren
- Asset Management - Konzeption SpecIF:contains NPK
- Asset Management - Konzeption SpecIF:contains Projektvariante zurückgestellt
- Asset Management - Portfoliomanagement SpecIF:contains Projektvariante verschieben oder stornieren
- 4:Investentscheidung fällen SpecIF:reads Projektmittelantrag
- Asset Management - Portfoliomanagement SpecIF:contains 4:Investentscheidung fällen
- 9:Projekt reviewen SpecIF:reads Projektakte - Dokumentation
- 9:Projekt reviewen SpecIF:writes Ablage Revision
- 9:Projekt reviewen SpecIF:writes Projektakte - Dokumentation [Review]
- Asset Management - Portfoliomanagement SpecIF:contains 9:Projekt reviewen
- Asset Management - Portfoliomanagement SpecIF:contains Projekt final abgeschlossen
- 6:Projekt realisieren SpecIF:reads Projektakte - Projektstudie [beauftragt]
- 6:Projekt realisieren SpecIF:writes Projektakte - Dokumentation
- Asset Service SpecIF:contains 6:Projekt realisieren
- 7:Verträge überwachen SpecIF:reads Vertrag Auftragnehmer (AN)
- 7:Verträge überwachen SpecIF:writes Terminplan [live]
- 7:Verträge überwachen SpecIF:writes Prognose: PUP, PAM, PLC
- Asset Service SpecIF:contains 7:Verträge überwachen
- Asset Service SpecIF:contains endEvent
- Asset Service SpecIF:contains PA
- 8:Planungsrunde durchführen SpecIF:reads Projektakte
- 8:Planungsrunde durchführen SpecIF:writes Projektakte
- Asset Service SpecIF:contains 8:Planungsrunde durchführen
- Asset Service SpecIF:contains Vertrag generiert
- Asset Service SpecIF:contains boundaryEvent
- Forking Exclusive Gateway: Soll das Projekt beantragt werden? SpecIF:signals Ja
- Ja SpecIF:triggers 3:Projekt beantragen
- Forking Exclusive Gateway: Soll das Projekt beantragt werden? SpecIF:signals Nein
- Nein SpecIF:triggers Projektvariante zurückgestellt
- NPK SpecIF:triggers Forking Exclusive Gateway: Soll das Projekt beantragt werden?
- 2:Projekt konzipieren SpecIF:signals NPK
- 1:Projekt initialisieren SpecIF:precedes 2:Projekt konzipieren
- Aufnahme des Projektes in die aktive Planung SpecIF:triggers 1:Projekt initialisieren
- 3:Projekt beantragen SpecIF:precedes 4:Investentscheidung fällen
- 4:Investentscheidung fällen SpecIF:precedes Forking Exclusive Gateway: Soll der Invest getätigt werden?
- PA SpecIF:triggers 9:Projekt reviewen
- 9:Projekt reviewen SpecIF:signals Projekt final abgeschlossen
- Forking Exclusive Gateway: Soll der Invest getätigt werden? SpecIF:signals Nein
- Nein SpecIF:triggers Projektvariante verschieben oder stornieren
- 6:Projekt realisieren SpecIF:signals PA
- boundaryEvent SpecIF:triggers 8:Planungsrunde durchführen
- Vertrag generiert SpecIF:triggers 7:Verträge überwachen
- 7:Verträge überwachen SpecIF:signals endEvent
- 8:Planungsrunde durchführen SpecIF:signals endEvent
- Forking Exclusive Gateway: Soll der Invest getätigt werden? SpecIF:precedes 6:Projekt realisieren
- Text Annotation 01 SpecIF:refersTo Aufnahme des Projektes in die aktive Planung
- Text Annotation 02 SpecIF:refersTo SNAP
- Text Annotation 04 SpecIF:refersTo 2:Projekt konzipieren
- Text Annotation 03 SpecIF:refersTo NPK
- Text Annotation 06 SpecIF:refersTo 9:Projekt reviewen
- Text Annotation 06 SpecIF:refersTo 6:Projekt realisieren
- Text Annotation 06 SpecIF:refersTo 3:Projekt beantragen
- Text Annotation 07 SpecIF:refersTo 2:Projekt konzipieren
- Text Annotation 07 SpecIF:refersTo 1:Projekt initialisieren
- Text Annotation 07 SpecIF:refersTo 3:Projekt beantragen
- Text Annotation 08 SpecIF:refersTo 6:Projekt realisieren
- Text Annotation 08 SpecIF:refersTo 1:Projekt initialisieren
- Text Annotation 08 SpecIF:refersTo 2:Projekt konzipieren
- Text Annotation 09 SpecIF:refersTo 6:Projekt realisieren
- Text Annotation 09 SpecIF:refersTo 9:Projekt reviewen
- EP_EV_HS_1_Einzelprojekt-HS SpecIF:shows Einzelprojekt HS
- EP_EV_HS_1_Einzelprojekt-HS SpecIF:shows Asset Management - Konzeption
- EP_EV_HS_1_Einzelprojekt-HS SpecIF:shows Asset Management - Portfoliomanagement
- EP_EV_HS_1_Einzelprojekt-HS SpecIF:shows Asset Service
- EP_EV_HS_1_Einzelprojekt-HS SpecIF:shows PSP Elemente Planung
- EP_EV_HS_1_Einzelprojekt-HS SpecIF:shows Projektakte - Projektstudie [konzipiert]
- EP_EV_HS_1_Einzelprojekt-HS SpecIF:shows Projektmittelantrag
- EP_EV_HS_1_Einzelprojekt-HS SpecIF:shows Projektakte - Projektstudie [beauftragt]
- EP_EV_HS_1_Einzelprojekt-HS SpecIF:shows Projektimpuls
- EP_EV_HS_1_Einzelprojekt-HS SpecIF:shows Projektakte [Variante_NPK1]
- EP_EV_HS_1_Einzelprojekt-HS SpecIF:shows SNAP
- EP_EV_HS_1_Einzelprojekt-HS SpecIF:shows Kalkulation
- EP_EV_HS_1_Einzelprojekt-HS SpecIF:shows Projektakte - Dokumentation [Review]
- EP_EV_HS_1_Einzelprojekt-HS SpecIF:shows Projektakte - Dokumentation
- EP_EV_HS_1_Einzelprojekt-HS SpecIF:shows Ablage Revision
- EP_EV_HS_1_Einzelprojekt-HS SpecIF:shows Prognose: PUP, PAM, PLC
- EP_EV_HS_1_Einzelprojekt-HS SpecIF:shows Terminplan [live]
- EP_EV_HS_1_Einzelprojekt-HS SpecIF:shows Vertrag Auftragnehmer (AN)
- EP_EV_HS_1_Einzelprojekt-HS SpecIF:shows Projektakte
- EP_EV_HS_1_Einzelprojekt-HS SpecIF:shows 3:Projekt beantragen
- EP_EV_HS_1_Einzelprojekt-HS SpecIF:shows Aufnahme des Projektes in die aktive Planung
- EP_EV_HS_1_Einzelprojekt-HS SpecIF:shows 1:Projekt initialisieren
- EP_EV_HS_1_Einzelprojekt-HS SpecIF:shows 2:Projekt konzipieren
- EP_EV_HS_1_Einzelprojekt-HS SpecIF:shows NPK
- EP_EV_HS_1_Einzelprojekt-HS SpecIF:shows Forking Exclusive Gateway: Soll das Projekt beantragt werden?
- EP_EV_HS_1_Einzelprojekt-HS SpecIF:shows Projektvariante zurückgestellt
- EP_EV_HS_1_Einzelprojekt-HS SpecIF:shows Projektvariante verschieben oder stornieren
- EP_EV_HS_1_Einzelprojekt-HS SpecIF:shows Forking Exclusive Gateway: Soll der Invest getätigt werden?
- EP_EV_HS_1_Einzelprojekt-HS SpecIF:shows 4:Investentscheidung fällen
- EP_EV_HS_1_Einzelprojekt-HS SpecIF:shows 9:Projekt reviewen
- EP_EV_HS_1_Einzelprojekt-HS SpecIF:shows Projekt final abgeschlossen
- EP_EV_HS_1_Einzelprojekt-HS SpecIF:shows 6:Projekt realisieren
- EP_EV_HS_1_Einzelprojekt-HS SpecIF:shows 7:Verträge überwachen
- EP_EV_HS_1_Einzelprojekt-HS SpecIF:shows endEvent
- EP_EV_HS_1_Einzelprojekt-HS SpecIF:shows PA
- EP_EV_HS_1_Einzelprojekt-HS SpecIF:shows 8:Planungsrunde durchführen
- EP_EV_HS_1_Einzelprojekt-HS SpecIF:shows Vertrag generiert
- EP_EV_HS_1_Einzelprojekt-HS SpecIF:shows boundaryEvent
- EP_EV_HS_1_Einzelprojekt-HS SpecIF:shows Ja
- EP_EV_HS_1_Einzelprojekt-HS SpecIF:shows Nein
- EP_EV_HS_1_Einzelprojekt-HS SpecIF:shows Nein
- HS Einzelprojekt - Projekt initialisieren SpecIF:contains Asset Management - Konzeption
- Initialer Projektimpuls erstellt SpecIF:writes Projektimpuls
- Asset Management - Konzeption SpecIF:contains Initialer Projektimpuls erstellt
- 10:Projektkategorie und Projekttyp ermitteln SpecIF:reads Projektimpuls
- 10:Projektkategorie und Projekttyp ermitteln SpecIF:reads SNAP
- 10:Projektkategorie und Projekttyp ermitteln SpecIF:writes Projektimpuls [Kat+Typ]
- Asset Management - Konzeption SpecIF:contains 10:Projektkategorie und Projekttyp ermitteln
- 11:Technische Lösung erarbeiten / überarbeiten SpecIF:reads Projektimpuls [Kat+Typ]
- 11:Technische Lösung erarbeiten / überarbeiten SpecIF:reads Langfristplanung
- 11:Technische Lösung erarbeiten / überarbeiten SpecIF:writes Projektakte [techn. Lösung]
- Asset Management - Konzeption SpecIF:contains 11:Technische Lösung erarbeiten / überarbeiten
- Asset Management - Konzeption SpecIF:contains Frist
- 12:Langfristplanung aktualisieren SpecIF:reads Projektakte [techn. Lösung]
- 12:Langfristplanung aktualisieren SpecIF:writes Langfristplanung
- Asset Management - Konzeption SpecIF:contains 12:Langfristplanung aktualisieren
- 13:Projektvarianten identifizieren SpecIF:reads Projektakte [techn. Lösung]
- 13:Projektvarianten identifizieren SpecIF:reads SNAP
- 13:Projektvarianten identifizieren SpecIF:writes Projektakte [Varianten]
- Asset Management - Konzeption SpecIF:contains 13:Projektvarianten identifizieren
- Projektvarianten bereit zur Konzeption SpecIF:reads Projektakte [Variante_NPK1]
- Asset Management - Konzeption SpecIF:contains Projektvarianten bereit zur Konzeption
- Asset Management - Konzeption SpecIF:contains Keine Projektvariante tauglich
- 17:Projektsteckbrief mit Protokoll abgleichen SpecIF:reads Projektakte [Varianten]
- 17:Projektsteckbrief mit Protokoll abgleichen SpecIF:reads NPK Protokoll
- 17:Projektsteckbrief mit Protokoll abgleichen SpecIF:reads Entscheidungsvorlage je Variante (Projektsteckbrief)
- 17:Projektsteckbrief mit Protokoll abgleichen SpecIF:writes Projektakte [Variante_NPK1]
- Asset Management - Konzeption SpecIF:contains 17:Projektsteckbrief mit Protokoll abgleichen
- 15:NPK Präsentation einreichen SpecIF:reads NPK Präsentation
- Asset Management - Konzeption SpecIF:contains 15:NPK Präsentation einreichen
- Asset Management - Konzeption SpecIF:contains NPK
- 14:NPK Präsentation vorbereiten SpecIF:reads Projektakte [Varianten]
- 14:NPK Präsentation vorbereiten SpecIF:writes Entscheidungsvorlage je Variante (Projektsteckbrief)
- 14:NPK Präsentation vorbereiten SpecIF:writes NPK Präsentation
- Asset Management - Konzeption SpecIF:contains 14:NPK Präsentation vorbereiten
- 16:Entscheidung aus NPK empfangen SpecIF:writes NPK Protokoll
- Asset Management - Konzeption SpecIF:contains 16:Entscheidung aus NPK empfangen
- Initialer Projektimpuls erstellt SpecIF:triggers 10:Projektkategorie und Projekttyp ermitteln
- 10:Projektkategorie und Projekttyp ermitteln SpecIF:precedes Joining Exclusive Gateway
- Joining Exclusive Gateway SpecIF:precedes 11:Technische Lösung erarbeiten / überarbeiten
- 11:Technische Lösung erarbeiten / überarbeiten SpecIF:precedes Forking Exclusive Gateway: Projekt im Projektprogramm Beginn <3 Jahre?
- Frist SpecIF:triggers Joining Exclusive Gateway
- Forking Exclusive Gateway: Projekt im Projektprogramm Beginn <3 Jahre? SpecIF:signals Nein
- Nein SpecIF:triggers 12:Langfristplanung aktualisieren
- Forking Exclusive Gateway: Projekt im Projektprogramm Beginn <3 Jahre? SpecIF:signals Ja
- Ja SpecIF:triggers 13:Projektvarianten identifizieren
- 12:Langfristplanung aktualisieren SpecIF:signals Frist
- NPK SpecIF:triggers 16:Entscheidung aus NPK empfangen
- 16:Entscheidung aus NPK empfangen SpecIF:precedes 17:Projektsteckbrief mit Protokoll abgleichen
- 13:Projektvarianten identifizieren SpecIF:precedes 14:NPK Präsentation vorbereiten
- 14:NPK Präsentation vorbereiten SpecIF:precedes 15:NPK Präsentation einreichen
- 15:NPK Präsentation einreichen SpecIF:signals NPK
- 17:Projektsteckbrief mit Protokoll abgleichen SpecIF:precedes Forking Exclusive Gateway: Anzahl Varianten >=1?
- Forking Exclusive Gateway: Anzahl Varianten >=1? SpecIF:signals nein
- nein SpecIF:triggers Keine Projektvariante tauglich
- Forking Exclusive Gateway: Anzahl Varianten >=1? SpecIF:signals ja
- ja SpecIF:triggers Projektvarianten bereit zur Konzeption
- Text Annotation 02 SpecIF:refersTo Projektakte [techn. Lösung]
- Text Annotation 03 SpecIF:refersTo Projektakte [Varianten]
- Text Annotation 01 SpecIF:refersTo Projektimpuls [Kat+Typ]
- Text Annotation 07 SpecIF:refersTo Projektimpuls
- Text Annotation 04 SpecIF:refersTo Entscheidungsvorlage je Variante (Projektsteckbrief)
- Text Annotation 05 SpecIF:refersTo NPK Protokoll
- Text Annotation 08 SpecIF:refersTo Langfristplanung
- Text Annotation 09 SpecIF:refersTo 10:Projektkategorie und Projekttyp ermitteln
- Text Annotation 10 SpecIF:refersTo SNAP
- Text Annotation 11 SpecIF:refersTo SNAP
- Text Annotation 12 SpecIF:refersTo 13:Projektvarianten identifizieren
- Text Annotation 06 SpecIF:refersTo Projektakte [Variante_NPK1]
- Text Annotation 13 SpecIF:refersTo NPK
- Text Annotation 14 SpecIF:refersTo 11:Technische Lösung erarbeiten / überarbeiten
- EP_EV_HS_1A_Einzelprojekt-HS--Projekt initialisieren SpecIF:shows HS Einzelprojekt - Projekt initialisieren
- EP_EV_HS_1A_Einzelprojekt-HS--Projekt initialisieren SpecIF:shows Asset Management - Konzeption
- EP_EV_HS_1A_Einzelprojekt-HS--Projekt initialisieren SpecIF:shows Projektimpuls
- EP_EV_HS_1A_Einzelprojekt-HS--Projekt initialisieren SpecIF:shows Projektakte [techn. Lösung]
- EP_EV_HS_1A_Einzelprojekt-HS--Projekt initialisieren SpecIF:shows Projektakte [Varianten]
- EP_EV_HS_1A_Einzelprojekt-HS--Projekt initialisieren SpecIF:shows Projektimpuls [Kat+Typ]
- EP_EV_HS_1A_Einzelprojekt-HS--Projekt initialisieren SpecIF:shows Langfristplanung
- EP_EV_HS_1A_Einzelprojekt-HS--Projekt initialisieren SpecIF:shows SNAP
- EP_EV_HS_1A_Einzelprojekt-HS--Projekt initialisieren SpecIF:shows NPK Protokoll
- EP_EV_HS_1A_Einzelprojekt-HS--Projekt initialisieren SpecIF:shows Projektakte [Variante_NPK1]
- EP_EV_HS_1A_Einzelprojekt-HS--Projekt initialisieren SpecIF:shows Entscheidungsvorlage je Variante (Projektsteckbrief)
- EP_EV_HS_1A_Einzelprojekt-HS--Projekt initialisieren SpecIF:shows NPK Präsentation
- EP_EV_HS_1A_Einzelprojekt-HS--Projekt initialisieren SpecIF:shows Initialer Projektimpuls erstellt
- EP_EV_HS_1A_Einzelprojekt-HS--Projekt initialisieren SpecIF:shows 10:Projektkategorie und Projekttyp ermitteln
- EP_EV_HS_1A_Einzelprojekt-HS--Projekt initialisieren SpecIF:shows 11:Technische Lösung erarbeiten / überarbeiten
- EP_EV_HS_1A_Einzelprojekt-HS--Projekt initialisieren SpecIF:shows Joining Exclusive Gateway
- EP_EV_HS_1A_Einzelprojekt-HS--Projekt initialisieren SpecIF:shows Forking Exclusive Gateway: Projekt im Projektprogramm Beginn <3 Jahre?
- EP_EV_HS_1A_Einzelprojekt-HS--Projekt initialisieren SpecIF:shows Frist
- EP_EV_HS_1A_Einzelprojekt-HS--Projekt initialisieren SpecIF:shows 12:Langfristplanung aktualisieren
- EP_EV_HS_1A_Einzelprojekt-HS--Projekt initialisieren SpecIF:shows 13:Projektvarianten identifizieren
- EP_EV_HS_1A_Einzelprojekt-HS--Projekt initialisieren SpecIF:shows Projektvarianten bereit zur Konzeption
- EP_EV_HS_1A_Einzelprojekt-HS--Projekt initialisieren SpecIF:shows Keine Projektvariante tauglich
- EP_EV_HS_1A_Einzelprojekt-HS--Projekt initialisieren SpecIF:shows Forking Exclusive Gateway: Anzahl Varianten >=1?
- EP_EV_HS_1A_Einzelprojekt-HS--Projekt initialisieren SpecIF:shows 17:Projektsteckbrief mit Protokoll abgleichen
- EP_EV_HS_1A_Einzelprojekt-HS--Projekt initialisieren SpecIF:shows 15:NPK Präsentation einreichen
- EP_EV_HS_1A_Einzelprojekt-HS--Projekt initialisieren SpecIF:shows NPK
- EP_EV_HS_1A_Einzelprojekt-HS--Projekt initialisieren SpecIF:shows 14:NPK Präsentation vorbereiten
- EP_EV_HS_1A_Einzelprojekt-HS--Projekt initialisieren SpecIF:shows 16:Entscheidung aus NPK empfangen
- EP_EV_HS_1A_Einzelprojekt-HS--Projekt initialisieren SpecIF:shows Nein
- EP_EV_HS_1A_Einzelprojekt-HS--Projekt initialisieren SpecIF:shows Ja
- EP_EV_HS_1A_Einzelprojekt-HS--Projekt initialisieren SpecIF:shows nein
- EP_EV_HS_1A_Einzelprojekt-HS--Projekt initialisieren SpecIF:shows ja
- HS Einzelprojekt - Projekt konzipieren SpecIF:contains Asset Management - Konzeption
- Projektvarianten bereit zur Konzeption SpecIF:writes Projektakte [Variante_NPK1]
- 18:Projekt je Variante konzipieren SpecIF:reads Projektakte [Variante_NPK1]
- 18:Projekt je Variante konzipieren SpecIF:reads SNAP (AVA?)
- 18:Projekt je Variante konzipieren SpecIF:writes Projektakte [RBAM/WiRe]
- 18:Projekt je Variante konzipieren SpecIF:writes SAP PS
- Asset Management - Konzeption SpecIF:contains 18:Projekt je Variante konzipieren
- 20:Typical basierte PSP Struktur erarbeiten SpecIF:reads Projektakte - Projektstudie [konzipiert]
- 20:Typical basierte PSP Struktur erarbeiten SpecIF:writes PSP Elemente Planung
- Asset Management - Konzeption SpecIF:contains 20:Typical basierte PSP Struktur erarbeiten
- 19:Projektstudie erstellen SpecIF:reads Projektakte [empfohl. Variante]
- 19:Projektstudie erstellen SpecIF:writes Projektakte - Projektstudie [konzipiert]
- Asset Management - Konzeption SpecIF:contains 19:Projektstudie erstellen
- Konzeption abgeschlossen SpecIF:reads PSP Elemente Planung
- Konzeption abgeschlossen SpecIF:reads Projektakte - Projektstudie [konzipiert]
- Asset Management - Konzeption SpecIF:contains Konzeption abgeschlossen
- 25:Variante empfehlen und festlegen SpecIF:reads Projektakte [RBAM/WiRe]
- 25:Variante empfehlen und festlegen SpecIF:writes Projektakte [empfohl. Variante]
- Asset Management - Konzeption SpecIF:contains 25:Variante empfehlen und festlegen
- Projektvarianten bereit zur Konzeption SpecIF:triggers 18:Projekt je Variante konzipieren
- 19:Projektstudie erstellen SpecIF:precedes 20:Typical basierte PSP Struktur erarbeiten
- 20:Typical basierte PSP Struktur erarbeiten SpecIF:signals Konzeption abgeschlossen
- 18:Projekt je Variante konzipieren SpecIF:precedes 25:Variante empfehlen und festlegen
- 25:Variante empfehlen und festlegen SpecIF:precedes 19:Projektstudie erstellen
- Text Annotation 02 SpecIF:refersTo SAP PS
- Text Annotation 01 SpecIF:refersTo SNAP (AVA?)
- Text Annotation 03 SpecIF:refersTo Projektakte - Projektstudie [konzipiert]
- Text Annotation 04 SpecIF:refersTo Projektakte [empfohl. Variante]
- Text Annotation 05 SpecIF:refersTo SNAP (AVA?)
- Text Annotation 06 SpecIF:refersTo PSP Elemente Planung
- EP_EV_HS_1B0_Einzelprojekt-HS--Projekt konzipieren SpecIF:shows HS Einzelprojekt - Projekt konzipieren
- EP_EV_HS_1B0_Einzelprojekt-HS--Projekt konzipieren SpecIF:shows Asset Management - Konzeption
- EP_EV_HS_1B0_Einzelprojekt-HS--Projekt konzipieren SpecIF:shows Projektakte [Variante_NPK1]
- EP_EV_HS_1B0_Einzelprojekt-HS--Projekt konzipieren SpecIF:shows Projektakte [RBAM/WiRe]
- EP_EV_HS_1B0_Einzelprojekt-HS--Projekt konzipieren SpecIF:shows SNAP (AVA?)
- EP_EV_HS_1B0_Einzelprojekt-HS--Projekt konzipieren SpecIF:shows SAP PS
- EP_EV_HS_1B0_Einzelprojekt-HS--Projekt konzipieren SpecIF:shows Projektakte - Projektstudie [konzipiert]
- EP_EV_HS_1B0_Einzelprojekt-HS--Projekt konzipieren SpecIF:shows Projektakte [empfohl. Variante]
- EP_EV_HS_1B0_Einzelprojekt-HS--Projekt konzipieren SpecIF:shows PSP Elemente Planung
- EP_EV_HS_1B0_Einzelprojekt-HS--Projekt konzipieren SpecIF:shows Projektvarianten bereit zur Konzeption
- EP_EV_HS_1B0_Einzelprojekt-HS--Projekt konzipieren SpecIF:shows 18:Projekt je Variante konzipieren
- EP_EV_HS_1B0_Einzelprojekt-HS--Projekt konzipieren SpecIF:shows 20:Typical basierte PSP Struktur erarbeiten
- EP_EV_HS_1B0_Einzelprojekt-HS--Projekt konzipieren SpecIF:shows 19:Projektstudie erstellen
- EP_EV_HS_1B0_Einzelprojekt-HS--Projekt konzipieren SpecIF:shows Konzeption abgeschlossen
- EP_EV_HS_1B0_Einzelprojekt-HS--Projekt konzipieren SpecIF:shows 25:Variante empfehlen und festlegen
- HS Einzelprojekt - Projekt konzipieren - Projekt je Variante konzipieren SpecIF:contains Asset Management - Konzeption
- HS Einzelprojekt - Projekt konzipieren - Projekt je Variante konzipieren SpecIF:contains DG-AMP
- 21:Planungsrecht klären SpecIF:reads Projektakte [Variante_NPK1]
- 21:Planungsrecht klären SpecIF:writes Projektakte [PlanungsrechtKlar]
- Asset Management - Konzeption SpecIF:contains 21:Planungsrecht klären
- 22:Technische Lösung auf Basis von Projekttypicals untersetzen SpecIF:reads Projektakte [PlanungsrechtKlar]
- 22:Technische Lösung auf Basis von Projekttypicals untersetzen SpecIF:writes Projektakte [techn. Lösung_Typicals]
- Asset Management - Konzeption SpecIF:contains 22:Technische Lösung auf Basis von Projekttypicals untersetzen
- 23:Kostenschätzung erstellen SpecIF:reads Projektakte [techn. Lösung_Typicals]
- 23:Kostenschätzung erstellen SpecIF:reads SNAP (AVA?)
- 23:Kostenschätzung erstellen SpecIF:writes Projektakte [Kostenschätzung]
- Asset Management - Konzeption SpecIF:contains 23:Kostenschätzung erstellen
- 24:WiRe und RBAM berechnen SpecIF:reads Projektakte [Kostenschätzung]
- 24:WiRe und RBAM berechnen SpecIF:writes Projektakte [RBAM/WiRe]
- DG-AMP SpecIF:contains 24:WiRe und RBAM berechnen
- Projekt für eine Variante konzipiert SpecIF:reads Projektakte [RBAM/WiRe]
- DG-AMP SpecIF:contains Projekt für eine Variante konzipiert
- Projektvarianten bereit zur Konzeption SpecIF:triggers 21:Planungsrecht klären
- 21:Planungsrecht klären SpecIF:precedes 22:Technische Lösung auf Basis von Projekttypicals untersetzen
- 22:Technische Lösung auf Basis von Projekttypicals untersetzen SpecIF:precedes 23:Kostenschätzung erstellen
- 23:Kostenschätzung erstellen SpecIF:precedes 24:WiRe und RBAM berechnen
- 24:WiRe und RBAM berechnen SpecIF:signals Projekt für eine Variante konzipiert
- Text Annotation 01 SpecIF:refersTo Projektakte [PlanungsrechtKlar]
- Text Annotation 02 SpecIF:refersTo Projektakte [techn. Lösung_Typicals]
- Text Annotation 03 SpecIF:refersTo Projektakte [Kostenschätzung]
- Text Annotation 04 SpecIF:refersTo SNAP (AVA?)
- Text Annotation 05 SpecIF:refersTo Projektakte [RBAM/WiRe]
- Text Annotation 06 SpecIF:refersTo 24:WiRe und RBAM berechnen
- EP_EV_HS_1B1_Einzelprojekt-HS--Projekt konzipieren--Projekt je Variante konzipieren SpecIF:shows HS Einzelprojekt - Projekt konzipieren - Projekt je Variante konzipieren
- EP_EV_HS_1B1_Einzelprojekt-HS--Projekt konzipieren--Projekt je Variante konzipieren SpecIF:shows Asset Management - Konzeption
- EP_EV_HS_1B1_Einzelprojekt-HS--Projekt konzipieren--Projekt je Variante konzipieren SpecIF:shows DG-AMP
- EP_EV_HS_1B1_Einzelprojekt-HS--Projekt konzipieren--Projekt je Variante konzipieren SpecIF:shows Projektakte [Variante_NPK1]
- EP_EV_HS_1B1_Einzelprojekt-HS--Projekt konzipieren--Projekt je Variante konzipieren SpecIF:shows Projektakte [PlanungsrechtKlar]
- EP_EV_HS_1B1_Einzelprojekt-HS--Projekt konzipieren--Projekt je Variante konzipieren SpecIF:shows Projektakte [techn. Lösung_Typicals]
- EP_EV_HS_1B1_Einzelprojekt-HS--Projekt konzipieren--Projekt je Variante konzipieren SpecIF:shows Projektakte [Kostenschätzung]
- EP_EV_HS_1B1_Einzelprojekt-HS--Projekt konzipieren--Projekt je Variante konzipieren SpecIF:shows SNAP (AVA?)
- EP_EV_HS_1B1_Einzelprojekt-HS--Projekt konzipieren--Projekt je Variante konzipieren SpecIF:shows Projektakte [RBAM/WiRe]
- EP_EV_HS_1B1_Einzelprojekt-HS--Projekt konzipieren--Projekt je Variante konzipieren SpecIF:shows Projektvarianten bereit zur Konzeption
- EP_EV_HS_1B1_Einzelprojekt-HS--Projekt konzipieren--Projekt je Variante konzipieren SpecIF:shows 21:Planungsrecht klären
- EP_EV_HS_1B1_Einzelprojekt-HS--Projekt konzipieren--Projekt je Variante konzipieren SpecIF:shows 22:Technische Lösung auf Basis von Projekttypicals untersetzen
- EP_EV_HS_1B1_Einzelprojekt-HS--Projekt konzipieren--Projekt je Variante konzipieren SpecIF:shows 23:Kostenschätzung erstellen
- EP_EV_HS_1B1_Einzelprojekt-HS--Projekt konzipieren--Projekt je Variante konzipieren SpecIF:shows 24:WiRe und RBAM berechnen
- EP_EV_HS_1B1_Einzelprojekt-HS--Projekt konzipieren--Projekt je Variante konzipieren SpecIF:shows Projekt für eine Variante konzipiert
- HS Einzelprojekt - Projekt konzipieren - Projektstudie erstellen SpecIF:contains Asset Management - Konzeption
- HS Einzelprojekt - Projekt konzipieren - Projektstudie erstellen SpecIF:contains DG-AMP
- HS Einzelprojekt - Projekt konzipieren - Projektstudie erstellen SpecIF:contains Asset Service - Designiertes Projektteam
- Projektstudie konzipiert SpecIF:reads Projektakte - Projektstudie [konzipiert]
- DG-AMP SpecIF:contains Projektstudie konzipiert
- 29:Kennzahlen nachberechnen SpecIF:reads Projektakte - Projektstudie [PlausiAS]
- 29:Kennzahlen nachberechnen SpecIF:writes Projektakte - Projektstudie [konzipiert]
- DG-AMP SpecIF:contains 29:Kennzahlen nachberechnen
- Projekt für eine Variante konzipiert SpecIF:writes Projektakte [empfohl. Variante]
- Asset Management - Konzeption SpecIF:contains Projekt für eine Variante konzipiert
- 26:Projektstudie entwerfen / überarbeiten SpecIF:reads Projektakte [empfohl. Variante]
- 26:Projektstudie entwerfen / überarbeiten SpecIF:reads Projektakte - Projektstudie [PlausiAS]
- 26:Projektstudie entwerfen / überarbeiten SpecIF:writes Projektakte - Projektstudie [entworfen]
- Asset Management - Konzeption SpecIF:contains 26:Projektstudie entwerfen / überarbeiten
- 28:Plausibilisierung prüfen SpecIF:reads Projektakte - Projektstudie [PlausiAS]
- 28:Plausibilisierung prüfen SpecIF:writes Projektakte - Projektstudie [PlausiAS]
- Asset Management - Konzeption SpecIF:contains 28:Plausibilisierung prüfen
- 27:Projektstudie plausibilisieren SpecIF:reads Projektakte - Projektstudie [entworfen]
- 27:Projektstudie plausibilisieren SpecIF:writes Projektakte - Projektstudie [PlausiAS]
- Asset Service - Designiertes Projektteam SpecIF:contains 27:Projektstudie plausibilisieren
- 29:Kennzahlen nachberechnen SpecIF:signals Projektstudie konzipiert
- Forking Exclusive Gateway: Prüfung ok? SpecIF:signals Ja
- Ja SpecIF:triggers 29:Kennzahlen nachberechnen
- Projekt für eine Variante konzipiert SpecIF:triggers Joining Exclusive Gateway
- Forking Exclusive Gateway: Prüfung ok? SpecIF:signals Nein
- Nein SpecIF:triggers Joining Exclusive Gateway
- 26:Projektstudie entwerfen / überarbeiten SpecIF:precedes 27:Projektstudie plausibilisieren
- 27:Projektstudie plausibilisieren SpecIF:precedes 28:Plausibilisierung prüfen
- 28:Plausibilisierung prüfen SpecIF:precedes Forking Exclusive Gateway: Prüfung ok?
- Joining Exclusive Gateway SpecIF:precedes 26:Projektstudie entwerfen / überarbeiten
- Text Annotation 01 SpecIF:refersTo Projektakte - Projektstudie [entworfen]
- Text Annotation 02 SpecIF:refersTo Projektakte - Projektstudie [konzipiert]
- Text Annotation 03 SpecIF:refersTo Projektakte - Projektstudie [PlausiAS]
- Text Annotation 04 SpecIF:refersTo 29:Kennzahlen nachberechnen
- EP_EV_HS_1B2_Einzelprojekt-HS--Projekt konzipieren--Projektstudie erstellen SpecIF:shows HS Einzelprojekt - Projekt konzipieren - Projektstudie erstellen
- EP_EV_HS_1B2_Einzelprojekt-HS--Projekt konzipieren--Projektstudie erstellen SpecIF:shows Asset Management - Konzeption
- EP_EV_HS_1B2_Einzelprojekt-HS--Projekt konzipieren--Projektstudie erstellen SpecIF:shows DG-AMP
- EP_EV_HS_1B2_Einzelprojekt-HS--Projekt konzipieren--Projektstudie erstellen SpecIF:shows Asset Service - Designiertes Projektteam
- EP_EV_HS_1B2_Einzelprojekt-HS--Projekt konzipieren--Projektstudie erstellen SpecIF:shows Projektakte - Projektstudie [konzipiert]
- EP_EV_HS_1B2_Einzelprojekt-HS--Projekt konzipieren--Projektstudie erstellen SpecIF:shows Projektakte - Projektstudie [PlausiAS]
- EP_EV_HS_1B2_Einzelprojekt-HS--Projekt konzipieren--Projektstudie erstellen SpecIF:shows Projektakte [empfohl. Variante]
- EP_EV_HS_1B2_Einzelprojekt-HS--Projekt konzipieren--Projektstudie erstellen SpecIF:shows Projektakte - Projektstudie [entworfen]
- EP_EV_HS_1B2_Einzelprojekt-HS--Projekt konzipieren--Projektstudie erstellen SpecIF:shows Projektstudie konzipiert
- EP_EV_HS_1B2_Einzelprojekt-HS--Projekt konzipieren--Projektstudie erstellen SpecIF:shows 29:Kennzahlen nachberechnen
- EP_EV_HS_1B2_Einzelprojekt-HS--Projekt konzipieren--Projektstudie erstellen SpecIF:shows Projekt für eine Variante konzipiert
- EP_EV_HS_1B2_Einzelprojekt-HS--Projekt konzipieren--Projektstudie erstellen SpecIF:shows 26:Projektstudie entwerfen / überarbeiten
- EP_EV_HS_1B2_Einzelprojekt-HS--Projekt konzipieren--Projektstudie erstellen SpecIF:shows 28:Plausibilisierung prüfen
- EP_EV_HS_1B2_Einzelprojekt-HS--Projekt konzipieren--Projektstudie erstellen SpecIF:shows 27:Projektstudie plausibilisieren
- EP_EV_HS_1B2_Einzelprojekt-HS--Projekt konzipieren--Projektstudie erstellen SpecIF:shows Joining Exclusive Gateway
- EP_EV_HS_1B2_Einzelprojekt-HS--Projekt konzipieren--Projektstudie erstellen SpecIF:shows Forking Exclusive Gateway: Prüfung ok?
- EP_EV_HS_1B2_Einzelprojekt-HS--Projekt konzipieren--Projektstudie erstellen SpecIF:shows Ja
- EP_EV_HS_1B2_Einzelprojekt-HS--Projekt konzipieren--Projektstudie erstellen SpecIF:shows Nein
- Projektprozess - Projekt beantragen SpecIF:contains Portfolio Management
- Projektprozess - Projekt beantragen SpecIF:contains Asset Management
- Projektprozess - Projekt beantragen SpecIF:contains Asset Management - Konzeption
- Konzeption abgeschlossen und in NPK bestätigt SpecIF:writes Projektakte - Projektstudie [konzipiert]
- Konzeption abgeschlossen und in NPK bestätigt SpecIF:writes PSP Elemente Planung
- Portfolio Management SpecIF:contains Konzeption abgeschlossen und in NPK bestätigt
- 30:PSP Struktur in SAP einpflegen SpecIF:reads Projektakte - Projektstudie [konzipiert]
- 30:PSP Struktur in SAP einpflegen SpecIF:writes SAP
- Portfolio Management SpecIF:contains 30:PSP Struktur in SAP einpflegen
- Projekt ist an PL übergeben SpecIF:reads Projektakte - Projektstudie [beauftragt]
- Portfolio Management SpecIF:contains Projekt ist an PL übergeben
- 34:Projekt an PL übergeben SpecIF:reads Projektakte - Projektstudie [konzipiert]
- 34:Projekt an PL übergeben SpecIF:writes Projektakte - Projektstudie [beauftragt]
- Portfolio Management SpecIF:contains 34:Projekt an PL übergeben
- 33:Projektstudie nacharbeiten SpecIF:reads Projektakte - Projektstudie [konzipiert]
- 33:Projektstudie nacharbeiten SpecIF:reads Protokoll Projektmittelantragsprüfung
- 33:Projektstudie nacharbeiten SpecIF:writes Projektakte - Projektstudie [konzipiert]
- Asset Management - Konzeption SpecIF:contains 33:Projektstudie nacharbeiten
- 32:Projektmittelantrag prüfen SpecIF:reads Projektmittelantrag
- 32:Projektmittelantrag prüfen SpecIF:writes Protokoll Projektmittelantragsprüfung
- Asset Management SpecIF:contains 32:Projektmittelantrag prüfen
- 31:Projektmittelantrag erstellen SpecIF:reads Projektakte - Projektstudie [konzipiert]
- 31:Projektmittelantrag erstellen SpecIF:writes Projektmittelantrag
- 31:Projektmittelantrag erstellen SpecIF:writes SAP
- Portfolio Management SpecIF:contains 31:Projektmittelantrag erstellen
- Konzeption abgeschlossen und in NPK bestätigt SpecIF:triggers Joining Exclusive Gateway
- 33:Projektstudie nacharbeiten SpecIF:precedes Joining Exclusive Gateway
- Joining Exclusive Gateway SpecIF:precedes 30:PSP Struktur in SAP einpflegen
- 30:PSP Struktur in SAP einpflegen SpecIF:precedes 31:Projektmittelantrag erstellen
- 31:Projektmittelantrag erstellen SpecIF:precedes 32:Projektmittelantrag prüfen
- 32:Projektmittelantrag prüfen SpecIF:precedes Forking Exclusive Gateway: Projektmittelantrag bewilligt?
- Forking Exclusive Gateway: Projektmittelantrag bewilligt? SpecIF:signals Nein - Projekt muss nachgearbeitet werden
- Nein - Projekt muss nachgearbeitet werden SpecIF:triggers 33:Projektstudie nacharbeiten
- Forking Exclusive Gateway: Projektmittelantrag bewilligt? SpecIF:signals Ja (Projekt bewilligt)
- Ja (Projekt bewilligt) SpecIF:triggers 34:Projekt an PL übergeben
- 34:Projekt an PL übergeben SpecIF:signals Projekt ist an PL übergeben
- Text Annotation 01 SpecIF:refersTo Projektakte - Projektstudie [beauftragt]
- Text Annotation 03 SpecIF:refersTo 32:Projektmittelantrag prüfen
- Text Annotation 02 SpecIF:refersTo Projektmittelantrag
- Text Annotation 04 SpecIF:refersTo SAP
- Text Annotation 05 SpecIF:refersTo 31:Projektmittelantrag erstellen
- EP_EV_HS_1C_Einzelprojekt-HS--Projekt-beantragen SpecIF:shows Projektprozess - Projekt beantragen
- EP_EV_HS_1C_Einzelprojekt-HS--Projekt-beantragen SpecIF:shows Portfolio Management
- EP_EV_HS_1C_Einzelprojekt-HS--Projekt-beantragen SpecIF:shows Asset Management
- EP_EV_HS_1C_Einzelprojekt-HS--Projekt-beantragen SpecIF:shows Asset Management - Konzeption
- EP_EV_HS_1C_Einzelprojekt-HS--Projekt-beantragen SpecIF:shows Projektakte - Projektstudie [konzipiert]
- EP_EV_HS_1C_Einzelprojekt-HS--Projekt-beantragen SpecIF:shows PSP Elemente Planung
- EP_EV_HS_1C_Einzelprojekt-HS--Projekt-beantragen SpecIF:shows SAP
- EP_EV_HS_1C_Einzelprojekt-HS--Projekt-beantragen SpecIF:shows Projektakte - Projektstudie [beauftragt]
- EP_EV_HS_1C_Einzelprojekt-HS--Projekt-beantragen SpecIF:shows Projektmittelantrag
- EP_EV_HS_1C_Einzelprojekt-HS--Projekt-beantragen SpecIF:shows Protokoll Projektmittelantragsprüfung
- EP_EV_HS_1C_Einzelprojekt-HS--Projekt-beantragen SpecIF:shows Joining Exclusive Gateway
- EP_EV_HS_1C_Einzelprojekt-HS--Projekt-beantragen SpecIF:shows Konzeption abgeschlossen und in NPK bestätigt
- EP_EV_HS_1C_Einzelprojekt-HS--Projekt-beantragen SpecIF:shows 30:PSP Struktur in SAP einpflegen
- EP_EV_HS_1C_Einzelprojekt-HS--Projekt-beantragen SpecIF:shows Forking Exclusive Gateway: Projektmittelantrag bewilligt?
- EP_EV_HS_1C_Einzelprojekt-HS--Projekt-beantragen SpecIF:shows Projekt ist an PL übergeben
- EP_EV_HS_1C_Einzelprojekt-HS--Projekt-beantragen SpecIF:shows 34:Projekt an PL übergeben
- EP_EV_HS_1C_Einzelprojekt-HS--Projekt-beantragen SpecIF:shows 33:Projektstudie nacharbeiten
- EP_EV_HS_1C_Einzelprojekt-HS--Projekt-beantragen SpecIF:shows 32:Projektmittelantrag prüfen
- EP_EV_HS_1C_Einzelprojekt-HS--Projekt-beantragen SpecIF:shows 31:Projektmittelantrag erstellen
- EP_EV_HS_1C_Einzelprojekt-HS--Projekt-beantragen SpecIF:shows Nein - Projekt muss nachgearbeitet werden
- EP_EV_HS_1C_Einzelprojekt-HS--Projekt-beantragen SpecIF:shows Ja (Projekt bewilligt)
- HS Einzelprojekt - Projekt realisieren SpecIF:contains Asset Service
- Verantwortung wurde formal von AM über LA an PL übergeben SpecIF:writes Projektakte - Projektstudie [beauftragt]
- Asset Service SpecIF:contains Verantwortung wurde formal von AM über LA an PL übergeben
- 35:Projekt grob planen SpecIF:reads Projektakte - Projektstudie [beauftragt]
- 35:Projekt grob planen SpecIF:writes Projektakte - Grobplanung
- Asset Service SpecIF:contains 35:Projekt grob planen
- Asset Service SpecIF:contains Projekt muss neu geplant werden
- Asset Service SpecIF:contains Projekt technisch fertig gemeldet
- 37:Projekt fein planen SpecIF:reads Projektakte - Grobplanung
- 37:Projekt fein planen SpecIF:writes Projektakte - Feinplanung [final]
- Asset Service SpecIF:contains 37:Projekt fein planen
- 38:Projekt ausführen SpecIF:reads Projektakte - Feinplanung [final]
- 38:Projekt ausführen SpecIF:writes Technische Fertigmeldungen
- 38:Projekt ausführen SpecIF:writes Projektakte - Dokumentation
- Asset Service SpecIF:contains 38:Projekt ausführen
- Asset Service SpecIF:contains Ausführungsfreigabe
- 36:TWE fällen SpecIF:reads Projektakte - Grobplanung
- Asset Service SpecIF:contains 36:TWE fällen
- 35:Projekt grob planen SpecIF:precedes 36:TWE fällen
- Verantwortung wurde formal von AM über LA an PL übergeben SpecIF:triggers 35:Projekt grob planen
- 36:TWE fällen SpecIF:precedes Forking Exclusive Gateway: TWE positiv?
- Forking Exclusive Gateway: TWE positiv? SpecIF:signals nein
- nein SpecIF:triggers Projekt muss neu geplant werden
- Forking Exclusive Gateway: TWE positiv? SpecIF:precedes 37:Projekt fein planen
- 38:Projekt ausführen SpecIF:signals Projekt technisch fertig gemeldet
- 37:Projekt fein planen SpecIF:signals Ausführungsfreigabe
- Ausführungsfreigabe SpecIF:triggers 38:Projekt ausführen
- Text Annotation 01 SpecIF:refersTo Ausführungsfreigabe
- EP_EV_HS_1D0_Einzelprojekt-HS--Projekt realisieren SpecIF:shows HS Einzelprojekt - Projekt realisieren
- EP_EV_HS_1D0_Einzelprojekt-HS--Projekt realisieren SpecIF:shows Asset Service
- EP_EV_HS_1D0_Einzelprojekt-HS--Projekt realisieren SpecIF:shows Projektakte - Projektstudie [beauftragt]
- EP_EV_HS_1D0_Einzelprojekt-HS--Projekt realisieren SpecIF:shows Projektakte - Grobplanung
- EP_EV_HS_1D0_Einzelprojekt-HS--Projekt realisieren SpecIF:shows Projektakte - Feinplanung [final]
- EP_EV_HS_1D0_Einzelprojekt-HS--Projekt realisieren SpecIF:shows Technische Fertigmeldungen
- EP_EV_HS_1D0_Einzelprojekt-HS--Projekt realisieren SpecIF:shows Projektakte - Dokumentation
- EP_EV_HS_1D0_Einzelprojekt-HS--Projekt realisieren SpecIF:shows Verantwortung wurde formal von AM über LA an PL übergeben
- EP_EV_HS_1D0_Einzelprojekt-HS--Projekt realisieren SpecIF:shows 35:Projekt grob planen
- EP_EV_HS_1D0_Einzelprojekt-HS--Projekt realisieren SpecIF:shows Forking Exclusive Gateway: TWE positiv?
- EP_EV_HS_1D0_Einzelprojekt-HS--Projekt realisieren SpecIF:shows Projekt muss neu geplant werden
- EP_EV_HS_1D0_Einzelprojekt-HS--Projekt realisieren SpecIF:shows Projekt technisch fertig gemeldet
- EP_EV_HS_1D0_Einzelprojekt-HS--Projekt realisieren SpecIF:shows 37:Projekt fein planen
- EP_EV_HS_1D0_Einzelprojekt-HS--Projekt realisieren SpecIF:shows 38:Projekt ausführen
- EP_EV_HS_1D0_Einzelprojekt-HS--Projekt realisieren SpecIF:shows Ausführungsfreigabe
- EP_EV_HS_1D0_Einzelprojekt-HS--Projekt realisieren SpecIF:shows 36:TWE fällen
- EP_EV_HS_1D0_Einzelprojekt-HS--Projekt realisieren SpecIF:shows nein
- HS Einzelprojekt -- Projekt realisieren - Projekt grob planen SpecIF:contains Asset Service - Bereichs- und Projektsteuerung
- HS Einzelprojekt -- Projekt realisieren - Projekt grob planen SpecIF:contains Asset Service - Lenkungsausschuss
- HS Einzelprojekt -- Projekt realisieren - Projekt grob planen SpecIF:contains Asset Service - Projektleitung
- HS Einzelprojekt -- Projekt realisieren - Projekt grob planen SpecIF:contains DG-AMP
- 39:Auftrag prüfen & ggf. mit AM / LA klären SpecIF:reads Projektakte - Projektstudie [beauftragt]
- 39:Auftrag prüfen & ggf. mit AM / LA klären SpecIF:reads Projektübersichts-Liste
- 39:Auftrag prüfen & ggf. mit AM / LA klären SpecIF:reads SNAP
- 39:Auftrag prüfen & ggf. mit AM / LA klären SpecIF:writes Projektannahme-Empfehlung [zur Freigabe]
- 39:Auftrag prüfen & ggf. mit AM / LA klären SpecIF:writes Gesamtkapazitätsplanung je Gruppe
- 39:Auftrag prüfen & ggf. mit AM / LA klären SpecIF:writes Organigramm
- 39:Auftrag prüfen & ggf. mit AM / LA klären SpecIF:writes Projektsteckbrief PL
- 39:Auftrag prüfen & ggf. mit AM / LA klären SpecIF:writes Abstimmungsprotokoll [AM]
- Asset Service - Projektleitung SpecIF:contains 39:Auftrag prüfen & ggf. mit AM / LA klären
- Asset Service - Projektleitung SpecIF:contains Verantwortung wurde formal von AM über LA an PL übergeben
- 40:Projekt zur Realisierung freigeben SpecIF:reads Projektannahme-Empfehlung [zur Freigabe]
- 40:Projekt zur Realisierung freigeben SpecIF:writes Projektannahme-Empfehlung [freigegeben]
- Asset Service - Lenkungsausschuss SpecIF:contains 40:Projekt zur Realisierung freigeben
- 41:PSP Elemente freigeben SpecIF:reads Projektannahme-Empfehlung [freigegeben]
- 41:PSP Elemente freigeben SpecIF:writes SAP PS
- Asset Service - Bereichs- und Projektsteuerung SpecIF:contains 41:PSP Elemente freigeben
- 43:Projekt planen SpecIF:reads Projektstrukturplan/PAM
- 43:Projekt planen SpecIF:writes Projektakte - Grobplanung
- 43:Projekt planen SpecIF:writes SAP PS
- Asset Service - Projektleitung SpecIF:contains 43:Projekt planen
- 42:Projekt aufsetzen SpecIF:reads Projektannahme-Empfehlung [freigegeben]
- 42:Projekt aufsetzen SpecIF:reads SAP PS
- 42:Projekt aufsetzen SpecIF:writes DMS
- 42:Projekt aufsetzen SpecIF:writes Projektstrukturplan/PAM
- 42:Projekt aufsetzen SpecIF:writes SAPCON
- Asset Service - Projektleitung SpecIF:contains 42:Projekt aufsetzen
- Grobplanung abgeschlossen SpecIF:reads Projektakte - Grobplanung
- Asset Service - Projektleitung SpecIF:contains Grobplanung abgeschlossen
- 44:WiRe und RBAM überarbeiten SpecIF:reads Projektakte - Grobplanung
- 44:WiRe und RBAM überarbeiten SpecIF:writes Projektakte - Grobplanung
- DG-AMP SpecIF:contains 44:WiRe und RBAM überarbeiten
- 39:Auftrag prüfen & ggf. mit AM / LA klären SpecIF:precedes 40:Projekt zur Realisierung freigeben
- Forking Exclusive Gateway: Grobplanung freigegeben? SpecIF:signals Nein
- Nein SpecIF:triggers Joining Exclusive Gateway
- Joining Exclusive Gateway SpecIF:precedes 39:Auftrag prüfen & ggf. mit AM / LA klären
- Verantwortung wurde formal von AM über LA an PL übergeben SpecIF:triggers Joining Exclusive Gateway
- 40:Projekt zur Realisierung freigeben SpecIF:precedes Forking Exclusive Gateway: Grobplanung freigegeben?
- Forking Exclusive Gateway: Grobplanung freigegeben? SpecIF:signals ja
- ja SpecIF:triggers 41:PSP Elemente freigeben
- 41:PSP Elemente freigeben SpecIF:precedes 42:Projekt aufsetzen
- 42:Projekt aufsetzen SpecIF:precedes 43:Projekt planen
- 43:Projekt planen SpecIF:precedes 44:WiRe und RBAM überarbeiten
- 44:WiRe und RBAM überarbeiten SpecIF:signals Grobplanung abgeschlossen
- Text Annotation 01 SpecIF:refersTo Projektakte - Projektstudie [beauftragt]
- Text Annotation 04 SpecIF:refersTo Projektsteckbrief PL
- Text Annotation 05 SpecIF:refersTo Organigramm
- Text Annotation 06 SpecIF:refersTo Projektakte - Grobplanung
- Text Annotation 03 SpecIF:refersTo Gesamtkapazitätsplanung je Gruppe
- Text Annotation 02 SpecIF:refersTo Abstimmungsprotokoll [AM]
- Text Annotation 07 SpecIF:refersTo Projektannahme-Empfehlung [freigegeben]
- Text Annotation 08 SpecIF:refersTo SNAP
- Text Annotation 09 SpecIF:refersTo 44:WiRe und RBAM überarbeiten
- EP_EV_HS_1D1_Einzelprojekt-HS--Projekt realisieren--Projekt grob planen SpecIF:shows HS Einzelprojekt -- Projekt realisieren - Projekt grob planen
- EP_EV_HS_1D1_Einzelprojekt-HS--Projekt realisieren--Projekt grob planen SpecIF:shows Asset Service - Bereichs- und Projektsteuerung
- EP_EV_HS_1D1_Einzelprojekt-HS--Projekt realisieren--Projekt grob planen SpecIF:shows Asset Service - Lenkungsausschuss
- EP_EV_HS_1D1_Einzelprojekt-HS--Projekt realisieren--Projekt grob planen SpecIF:shows Asset Service - Projektleitung
- EP_EV_HS_1D1_Einzelprojekt-HS--Projekt realisieren--Projekt grob planen SpecIF:shows DG-AMP
- EP_EV_HS_1D1_Einzelprojekt-HS--Projekt realisieren--Projekt grob planen SpecIF:shows Projektakte - Projektstudie [beauftragt]
- EP_EV_HS_1D1_Einzelprojekt-HS--Projekt realisieren--Projekt grob planen SpecIF:shows Projektannahme-Empfehlung [zur Freigabe]
- EP_EV_HS_1D1_Einzelprojekt-HS--Projekt realisieren--Projekt grob planen SpecIF:shows Projektsteckbrief PL
- EP_EV_HS_1D1_Einzelprojekt-HS--Projekt realisieren--Projekt grob planen SpecIF:shows Organigramm
- EP_EV_HS_1D1_Einzelprojekt-HS--Projekt realisieren--Projekt grob planen SpecIF:shows Projektannahme-Empfehlung [freigegeben]
- EP_EV_HS_1D1_Einzelprojekt-HS--Projekt realisieren--Projekt grob planen SpecIF:shows SAP PS
- EP_EV_HS_1D1_Einzelprojekt-HS--Projekt realisieren--Projekt grob planen SpecIF:shows Projektakte - Grobplanung
- EP_EV_HS_1D1_Einzelprojekt-HS--Projekt realisieren--Projekt grob planen SpecIF:shows Projektstrukturplan/PAM
- EP_EV_HS_1D1_Einzelprojekt-HS--Projekt realisieren--Projekt grob planen SpecIF:shows Gesamtkapazitätsplanung je Gruppe
- EP_EV_HS_1D1_Einzelprojekt-HS--Projekt realisieren--Projekt grob planen SpecIF:shows Abstimmungsprotokoll [AM]
- EP_EV_HS_1D1_Einzelprojekt-HS--Projekt realisieren--Projekt grob planen SpecIF:shows DMS
- EP_EV_HS_1D1_Einzelprojekt-HS--Projekt realisieren--Projekt grob planen SpecIF:shows SAPCON
- EP_EV_HS_1D1_Einzelprojekt-HS--Projekt realisieren--Projekt grob planen SpecIF:shows Projektübersichts-Liste
- EP_EV_HS_1D1_Einzelprojekt-HS--Projekt realisieren--Projekt grob planen SpecIF:shows SNAP
- EP_EV_HS_1D1_Einzelprojekt-HS--Projekt realisieren--Projekt grob planen SpecIF:shows 39:Auftrag prüfen & ggf. mit AM / LA klären
- EP_EV_HS_1D1_Einzelprojekt-HS--Projekt realisieren--Projekt grob planen SpecIF:shows Verantwortung wurde formal von AM über LA an PL übergeben
- EP_EV_HS_1D1_Einzelprojekt-HS--Projekt realisieren--Projekt grob planen SpecIF:shows Joining Exclusive Gateway
- EP_EV_HS_1D1_Einzelprojekt-HS--Projekt realisieren--Projekt grob planen SpecIF:shows 40:Projekt zur Realisierung freigeben
- EP_EV_HS_1D1_Einzelprojekt-HS--Projekt realisieren--Projekt grob planen SpecIF:shows Forking Exclusive Gateway: Grobplanung freigegeben?
- EP_EV_HS_1D1_Einzelprojekt-HS--Projekt realisieren--Projekt grob planen SpecIF:shows 41:PSP Elemente freigeben
- EP_EV_HS_1D1_Einzelprojekt-HS--Projekt realisieren--Projekt grob planen SpecIF:shows 43:Projekt planen
- EP_EV_HS_1D1_Einzelprojekt-HS--Projekt realisieren--Projekt grob planen SpecIF:shows 42:Projekt aufsetzen
- EP_EV_HS_1D1_Einzelprojekt-HS--Projekt realisieren--Projekt grob planen SpecIF:shows Grobplanung abgeschlossen
- EP_EV_HS_1D1_Einzelprojekt-HS--Projekt realisieren--Projekt grob planen SpecIF:shows 44:WiRe und RBAM überarbeiten
- EP_EV_HS_1D1_Einzelprojekt-HS--Projekt realisieren--Projekt grob planen SpecIF:shows Nein
- EP_EV_HS_1D1_Einzelprojekt-HS--Projekt realisieren--Projekt grob planen SpecIF:shows ja
- HS Einzelprojekt - Projekt realisieren - Projekt grob planen - Projekt aufsetzen SpecIF:contains Asset Service - Projektleitung
- PSP Elemente sind freigegeben SpecIF:writes Projektannahme-Empfehlung [freigegeben]
- Asset Service - Projektleitung SpecIF:contains PSP Elemente sind freigegeben
- 45:Projektinfrastruktur anlegen SpecIF:reads SAP PS
- 45:Projektinfrastruktur anlegen SpecIF:reads Organigramm
- 45:Projektinfrastruktur anlegen SpecIF:reads Projektannahme-Empfehlung [freigegeben]
- 45:Projektinfrastruktur anlegen SpecIF:reads AVA
- 45:Projektinfrastruktur anlegen SpecIF:reads SNAP
- 45:Projektinfrastruktur anlegen SpecIF:writes DMS
- 45:Projektinfrastruktur anlegen SpecIF:writes SAPCON
- 45:Projektinfrastruktur anlegen SpecIF:writes AVA
- Asset Service - Projektleitung SpecIF:contains 45:Projektinfrastruktur anlegen
- 46:Projektstrukturplan anlegen SpecIF:reads Projektakte - Projektstudie [beauftragt]
- 46:Projektstrukturplan anlegen SpecIF:reads Abstimmungsprotokoll [AM]
- 46:Projektstrukturplan anlegen SpecIF:writes Projektstrukturplan/PAM
- Asset Service - Projektleitung SpecIF:contains 46:Projektstrukturplan anlegen
- Asset Service - Projektleitung SpecIF:contains Kickoff durchgeführt
- Projekt initial aufgesetzt SpecIF:reads Projektstrukturplan/PAM
- Asset Service - Projektleitung SpecIF:contains Projekt initial aufgesetzt
- 47:Beschaffung von externen Dienstleistern SpecIF:reads Projektstrukturplan/PAM
- 47:Beschaffung von externen Dienstleistern SpecIF:reads SAP (BANF)
- 47:Beschaffung von externen Dienstleistern SpecIF:reads AVA
- 47:Beschaffung von externen Dienstleistern SpecIF:writes SAP (BANF)
- Asset Service - Projektleitung SpecIF:contains 47:Beschaffung von externen Dienstleistern
- PSP Elemente sind freigegeben SpecIF:triggers 45:Projektinfrastruktur anlegen
- 45:Projektinfrastruktur anlegen SpecIF:signals Kickoff durchgeführt
- Kickoff durchgeführt SpecIF:triggers 46:Projektstrukturplan anlegen
- 46:Projektstrukturplan anlegen SpecIF:precedes Forking Exclusive Gateway: Sind externe Planer erforderlich?
- Forking Exclusive Gateway: Sind externe Planer erforderlich? SpecIF:signals Ja
- Ja SpecIF:triggers 47:Beschaffung von externen Dienstleistern
- Forking Exclusive Gateway: Sind externe Planer erforderlich? SpecIF:signals Nein
- Nein SpecIF:triggers Joining Exclusive Gateway
- 47:Beschaffung von externen Dienstleistern SpecIF:precedes Joining Exclusive Gateway
- Joining Exclusive Gateway SpecIF:signals Projekt initial aufgesetzt
- Text Annotation 01 SpecIF:refersTo SAP (BANF)
- Text Annotation 02 SpecIF:refersTo AVA
- Text Annotation 03 SpecIF:refersTo Projektstrukturplan/PAM
- Text Annotation 06 SpecIF:refersTo Kickoff durchgeführt
- Text Annotation 07 SpecIF:refersTo SAP (BANF)
- Text Annotation 04 SpecIF:refersTo DMS
- Text Annotation 05 SpecIF:refersTo SAPCON
- Text Annotation 08 SpecIF:refersTo 45:Projektinfrastruktur anlegen
- Text Annotation 09 SpecIF:refersTo SNAP
- EP_EV_HS_1D2_Einzelprojekt-HS--Projekt realisieren--Projekt grob planen--Projekt grob planen--Projekt aufsetzen SpecIF:shows HS Einzelprojekt - Projekt realisieren - Projekt grob planen - Projekt aufsetzen
- EP_EV_HS_1D2_Einzelprojekt-HS--Projekt realisieren--Projekt grob planen--Projekt grob planen--Projekt aufsetzen SpecIF:shows Asset Service - Projektleitung
- EP_EV_HS_1D2_Einzelprojekt-HS--Projekt realisieren--Projekt grob planen--Projekt grob planen--Projekt aufsetzen SpecIF:shows Projektannahme-Empfehlung [freigegeben]
- EP_EV_HS_1D2_Einzelprojekt-HS--Projekt realisieren--Projekt grob planen--Projekt grob planen--Projekt aufsetzen SpecIF:shows Organigramm
- EP_EV_HS_1D2_Einzelprojekt-HS--Projekt realisieren--Projekt grob planen--Projekt grob planen--Projekt aufsetzen SpecIF:shows SAP PS
- EP_EV_HS_1D2_Einzelprojekt-HS--Projekt realisieren--Projekt grob planen--Projekt grob planen--Projekt aufsetzen SpecIF:shows AVA
- EP_EV_HS_1D2_Einzelprojekt-HS--Projekt realisieren--Projekt grob planen--Projekt grob planen--Projekt aufsetzen SpecIF:shows SNAP
- EP_EV_HS_1D2_Einzelprojekt-HS--Projekt realisieren--Projekt grob planen--Projekt grob planen--Projekt aufsetzen SpecIF:shows Projektakte - Projektstudie [beauftragt]
- EP_EV_HS_1D2_Einzelprojekt-HS--Projekt realisieren--Projekt grob planen--Projekt grob planen--Projekt aufsetzen SpecIF:shows Abstimmungsprotokoll [AM]
- EP_EV_HS_1D2_Einzelprojekt-HS--Projekt realisieren--Projekt grob planen--Projekt grob planen--Projekt aufsetzen SpecIF:shows Projektstrukturplan/PAM
- EP_EV_HS_1D2_Einzelprojekt-HS--Projekt realisieren--Projekt grob planen--Projekt grob planen--Projekt aufsetzen SpecIF:shows SAP (BANF)
- EP_EV_HS_1D2_Einzelprojekt-HS--Projekt realisieren--Projekt grob planen--Projekt grob planen--Projekt aufsetzen SpecIF:shows DMS
- EP_EV_HS_1D2_Einzelprojekt-HS--Projekt realisieren--Projekt grob planen--Projekt grob planen--Projekt aufsetzen SpecIF:shows SAPCON
- EP_EV_HS_1D2_Einzelprojekt-HS--Projekt realisieren--Projekt grob planen--Projekt grob planen--Projekt aufsetzen SpecIF:shows PSP Elemente sind freigegeben
- EP_EV_HS_1D2_Einzelprojekt-HS--Projekt realisieren--Projekt grob planen--Projekt grob planen--Projekt aufsetzen SpecIF:shows 45:Projektinfrastruktur anlegen
- EP_EV_HS_1D2_Einzelprojekt-HS--Projekt realisieren--Projekt grob planen--Projekt grob planen--Projekt aufsetzen SpecIF:shows 46:Projektstrukturplan anlegen
- EP_EV_HS_1D2_Einzelprojekt-HS--Projekt realisieren--Projekt grob planen--Projekt grob planen--Projekt aufsetzen SpecIF:shows Kickoff durchgeführt
- EP_EV_HS_1D2_Einzelprojekt-HS--Projekt realisieren--Projekt grob planen--Projekt grob planen--Projekt aufsetzen SpecIF:shows Forking Exclusive Gateway: Sind externe Planer erforderlich?
- EP_EV_HS_1D2_Einzelprojekt-HS--Projekt realisieren--Projekt grob planen--Projekt grob planen--Projekt aufsetzen SpecIF:shows Joining Exclusive Gateway
- EP_EV_HS_1D2_Einzelprojekt-HS--Projekt realisieren--Projekt grob planen--Projekt grob planen--Projekt aufsetzen SpecIF:shows Projekt initial aufgesetzt
- EP_EV_HS_1D2_Einzelprojekt-HS--Projekt realisieren--Projekt grob planen--Projekt grob planen--Projekt aufsetzen SpecIF:shows 47:Beschaffung von externen Dienstleistern
- EP_EV_HS_1D2_Einzelprojekt-HS--Projekt realisieren--Projekt grob planen--Projekt grob planen--Projekt aufsetzen SpecIF:shows Ja
- EP_EV_HS_1D2_Einzelprojekt-HS--Projekt realisieren--Projekt grob planen--Projekt grob planen--Projekt aufsetzen SpecIF:shows Nein
- HS Einzelprojekt - Projekt realisieren - Projekt grob planen - Projekt planen SpecIF:contains Asset Service - Projektleitung
- HS Einzelprojekt - Projekt realisieren - Projekt grob planen - Projekt planen SpecIF:contains Asset Service - Teilprojektleitung (Hoch- und Tiefbau, Kabelbau, Anlagenbau)
- Projekt initial aufgesetzt SpecIF:writes Projektstrukturplan/PAM
- Asset Service - Teilprojektleitung (Hoch- und Tiefbau, Kabelbau, Anlagenbau) SpecIF:contains Projekt initial aufgesetzt
- 48:Entwurfsplanung SpecIF:reads Standardzahlplan
- 48:Entwurfsplanung SpecIF:reads Projektstrukturplan/PAM
- 48:Entwurfsplanung SpecIF:writes Grobterminplan
- 48:Entwurfsplanung SpecIF:writes Zahlplan [Entwurf]
- 48:Entwurfsplanung SpecIF:writes Projektakte - PL-Entwurfsplanung
- 48:Entwurfsplanung SpecIF:writes Projektstrukturplan/PAM
- Asset Service - Projektleitung SpecIF:contains 48:Entwurfsplanung
- 49:Leistungen konkretisieren SpecIF:reads AVA
- 49:Leistungen konkretisieren SpecIF:reads Projektstrukturplan/PAM
- 49:Leistungen konkretisieren SpecIF:reads SNAP
- 49:Leistungen konkretisieren SpecIF:writes AVA
- Asset Service - Teilprojektleitung (Hoch- und Tiefbau, Kabelbau, Anlagenbau) SpecIF:contains 49:Leistungen konkretisieren
- 50:Entwurfsplanung SpecIF:reads Projektstrukturplan/PAM
- 50:Entwurfsplanung SpecIF:writes Projektakte - TP-Entwurfsplanung
- Asset Service - Teilprojektleitung (Hoch- und Tiefbau, Kabelbau, Anlagenbau) SpecIF:contains 50:Entwurfsplanung
- 52:Vergabeeinheiten erstellen SpecIF:reads AVA
- 52:Vergabeeinheiten erstellen SpecIF:writes AVA
- Asset Service - Projektleitung SpecIF:contains 52:Vergabeeinheiten erstellen
- 53:Leistungspositionen den Vergabeeinheiten zuordnen SpecIF:reads AVA
- 53:Leistungspositionen den Vergabeeinheiten zuordnen SpecIF:writes AVA
- Asset Service - Projektleitung SpecIF:contains 53:Leistungspositionen den Vergabeeinheiten zuordnen
- 55:Voraussichtliche Beschaffungsdauer ermitteln SpecIF:reads AVA
- 55:Voraussichtliche Beschaffungsdauer ermitteln SpecIF:reads Grobterminplan
- 55:Voraussichtliche Beschaffungsdauer ermitteln SpecIF:writes Eckterminplan [inkl. Beschaffungsprozess]
- Asset Service - Projektleitung SpecIF:contains 55:Voraussichtliche Beschaffungsdauer ermitteln
- 54:Zahlungsbedingung pro Vergabeeinheit definieren SpecIF:reads AVA
- 54:Zahlungsbedingung pro Vergabeeinheit definieren SpecIF:reads Zahlplan [Entwurf]
- 54:Zahlungsbedingung pro Vergabeeinheit definieren SpecIF:writes Zahlplan [individuell für jede VE]
- Asset Service - Projektleitung SpecIF:contains 54:Zahlungsbedingung pro Vergabeeinheit definieren
- 57:Grobplanung erstellen SpecIF:reads Projektstrukturplan/PAM
- 57:Grobplanung erstellen SpecIF:reads Projektakte - Projektstudie [beauftragt]
- 57:Grobplanung erstellen SpecIF:reads SAP PS
- 57:Grobplanung erstellen SpecIF:reads Projektakte - TP-Grobplanung
- 57:Grobplanung erstellen SpecIF:reads Eckterminplan [inkl. Beschaffungsprozess]
- 57:Grobplanung erstellen SpecIF:reads Zahlplan [individuell für jede VE]
- 57:Grobplanung erstellen SpecIF:reads Projektakte - PL-Entwurfsplanung
- 57:Grobplanung erstellen SpecIF:reads AVA
- 57:Grobplanung erstellen SpecIF:reads SNAP
- 57:Grobplanung erstellen SpecIF:writes Projektakte - Grobplanung
- 57:Grobplanung erstellen SpecIF:writes AVA
- 57:Grobplanung erstellen SpecIF:writes Gesamtkapazitätsplanung - Unternehmen
- Asset Service - Projektleitung SpecIF:contains 57:Grobplanung erstellen
- 51:Genehmigungsplanung SpecIF:reads Projektstrukturplan/PAM
- 51:Genehmigungsplanung SpecIF:reads Projektakte - TP-Entwurfsplanung
- 51:Genehmigungsplanung SpecIF:writes Projektakte - TP-Genehmigungsplanung
- Asset Service - Teilprojektleitung (Hoch- und Tiefbau, Kabelbau, Anlagenbau) SpecIF:contains 51:Genehmigungsplanung
- Grobplanung erstellt SpecIF:reads Projektakte - Grobplanung
- Asset Service - Projektleitung SpecIF:contains Grobplanung erstellt
- 56:TP-Grobplanung erstellen SpecIF:reads Projektstrukturplan/PAM
- 56:TP-Grobplanung erstellen SpecIF:reads Projektakte - TP-Genehmigungsplanung
- 56:TP-Grobplanung erstellen SpecIF:reads Projektakte - TP-Entwurfsplanung
- 56:TP-Grobplanung erstellen SpecIF:reads AVA
- 56:TP-Grobplanung erstellen SpecIF:reads SNAP
- 56:TP-Grobplanung erstellen SpecIF:writes Projektakte - TP-Grobplanung
- 56:TP-Grobplanung erstellen SpecIF:writes AVA
- Asset Service - Teilprojektleitung (Hoch- und Tiefbau, Kabelbau, Anlagenbau) SpecIF:contains 56:TP-Grobplanung erstellen
- 49:Leistungen konkretisieren SpecIF:precedes Joining Parallel Gateway
- Forking Parallel Gateway SpecIF:precedes 50:Entwurfsplanung
- Projekt initial aufgesetzt SpecIF:triggers Forking Parallel Gateway
- Forking Parallel Gateway SpecIF:precedes 49:Leistungen konkretisieren
- Forking Parallel Gateway SpecIF:precedes 48:Entwurfsplanung
- 48:Entwurfsplanung SpecIF:precedes Joining Parallel Gateway
- 50:Entwurfsplanung SpecIF:precedes Joining Parallel Gateway
- Joining Parallel Gateway SpecIF:precedes Forking Parallel Gateway
- Forking Parallel Gateway SpecIF:precedes 52:Vergabeeinheiten erstellen
- 52:Vergabeeinheiten erstellen SpecIF:precedes 53:Leistungspositionen den Vergabeeinheiten zuordnen
- 53:Leistungspositionen den Vergabeeinheiten zuordnen SpecIF:precedes 54:Zahlungsbedingung pro Vergabeeinheit definieren
- 54:Zahlungsbedingung pro Vergabeeinheit definieren SpecIF:precedes 55:Voraussichtliche Beschaffungsdauer ermitteln
- 55:Voraussichtliche Beschaffungsdauer ermitteln SpecIF:precedes Joining Parallel Gateway
- Joining Exclusive Gateway SpecIF:precedes Joining Parallel Gateway
- 56:TP-Grobplanung erstellen SpecIF:precedes 57:Grobplanung erstellen
- 57:Grobplanung erstellen SpecIF:signals Grobplanung erstellt
- Forking Parallel Gateway SpecIF:precedes Forking Exclusive Gateway: Genehmigungsplanung erforderlich?
- Joining Parallel Gateway SpecIF:precedes 56:TP-Grobplanung erstellen
- Forking Exclusive Gateway: Genehmigungsplanung erforderlich? SpecIF:signals Nein
- Nein SpecIF:triggers Joining Exclusive Gateway
- Forking Exclusive Gateway: Genehmigungsplanung erforderlich? SpecIF:signals Ja
- Ja SpecIF:triggers 51:Genehmigungsplanung
- 51:Genehmigungsplanung SpecIF:precedes Joining Exclusive Gateway
- Text Annotation 01 SpecIF:refersTo 49:Leistungen konkretisieren
- Text Annotation 02 SpecIF:refersTo Standardzahlplan
- Text Annotation 03 SpecIF:refersTo Zahlplan [Entwurf]
- Text Annotation 04 SpecIF:refersTo Projektakte - Grobplanung
- Text Annotation 05 SpecIF:refersTo Gesamtkapazitätsplanung - Unternehmen
- Text Annotation 06 SpecIF:refersTo Projektakte - TP-Genehmigungsplanung
- Text Annotation 07 SpecIF:refersTo Projektakte - TP-Entwurfsplanung
- Text Annotation 08 SpecIF:refersTo Eckterminplan [inkl. Beschaffungsprozess]
- Text Annotation 09 SpecIF:refersTo AVA
- Text Annotation 10 SpecIF:refersTo 49:Leistungen konkretisieren
- Text Annotation 11 SpecIF:refersTo Projektakte - TP-Grobplanung
- Text Annotation 12 SpecIF:refersTo AVA
- Text Annotation 12 SpecIF:refersTo SNAP
- Text Annotation 13 SpecIF:refersTo SNAP
- Text Annotation 14 SpecIF:refersTo AVA
- Text Annotation 14 SpecIF:refersTo SNAP
- Text Annotation 15 SpecIF:refersTo SNAP
- Text Annotation 16 SpecIF:refersTo Projektakte - PL-Entwurfsplanung
- EP_EV_HS_1D3_Einzelprojekt-HS--Projekt realisieren--Projekt grob planen--Projekt grob planen--Projekt planen SpecIF:shows HS Einzelprojekt - Projekt realisieren - Projekt grob planen - Projekt planen
- EP_EV_HS_1D3_Einzelprojekt-HS--Projekt realisieren--Projekt grob planen--Projekt grob planen--Projekt planen SpecIF:shows Asset Service - Projektleitung
- EP_EV_HS_1D3_Einzelprojekt-HS--Projekt realisieren--Projekt grob planen--Projekt grob planen--Projekt planen SpecIF:shows Asset Service - Teilprojektleitung (Hoch- und Tiefbau, Kabelbau, Anlagenbau)
- EP_EV_HS_1D3_Einzelprojekt-HS--Projekt realisieren--Projekt grob planen--Projekt grob planen--Projekt planen SpecIF:shows Projektstrukturplan/PAM
- EP_EV_HS_1D3_Einzelprojekt-HS--Projekt realisieren--Projekt grob planen--Projekt grob planen--Projekt planen SpecIF:shows Projektakte - PL-Entwurfsplanung
- EP_EV_HS_1D3_Einzelprojekt-HS--Projekt realisieren--Projekt grob planen--Projekt grob planen--Projekt planen SpecIF:shows Zahlplan [Entwurf]
- EP_EV_HS_1D3_Einzelprojekt-HS--Projekt realisieren--Projekt grob planen--Projekt grob planen--Projekt planen SpecIF:shows Standardzahlplan
- EP_EV_HS_1D3_Einzelprojekt-HS--Projekt realisieren--Projekt grob planen--Projekt grob planen--Projekt planen SpecIF:shows AVA
- EP_EV_HS_1D3_Einzelprojekt-HS--Projekt realisieren--Projekt grob planen--Projekt grob planen--Projekt planen SpecIF:shows Zahlplan [individuell für jede VE]
- EP_EV_HS_1D3_Einzelprojekt-HS--Projekt realisieren--Projekt grob planen--Projekt grob planen--Projekt planen SpecIF:shows Eckterminplan [inkl. Beschaffungsprozess]
- EP_EV_HS_1D3_Einzelprojekt-HS--Projekt realisieren--Projekt grob planen--Projekt grob planen--Projekt planen SpecIF:shows Gesamtkapazitätsplanung - Unternehmen
- EP_EV_HS_1D3_Einzelprojekt-HS--Projekt realisieren--Projekt grob planen--Projekt grob planen--Projekt planen SpecIF:shows Projektakte - Grobplanung
- EP_EV_HS_1D3_Einzelprojekt-HS--Projekt realisieren--Projekt grob planen--Projekt grob planen--Projekt planen SpecIF:shows Projektakte - TP-Genehmigungsplanung
- EP_EV_HS_1D3_Einzelprojekt-HS--Projekt realisieren--Projekt grob planen--Projekt grob planen--Projekt planen SpecIF:shows Projektakte - TP-Entwurfsplanung
- EP_EV_HS_1D3_Einzelprojekt-HS--Projekt realisieren--Projekt grob planen--Projekt grob planen--Projekt planen SpecIF:shows Grobterminplan
- EP_EV_HS_1D3_Einzelprojekt-HS--Projekt realisieren--Projekt grob planen--Projekt grob planen--Projekt planen SpecIF:shows Projektakte - TP-Grobplanung
- EP_EV_HS_1D3_Einzelprojekt-HS--Projekt realisieren--Projekt grob planen--Projekt grob planen--Projekt planen SpecIF:shows Projektakte - Projektstudie [beauftragt]
- EP_EV_HS_1D3_Einzelprojekt-HS--Projekt realisieren--Projekt grob planen--Projekt grob planen--Projekt planen SpecIF:shows SAP PS
- EP_EV_HS_1D3_Einzelprojekt-HS--Projekt realisieren--Projekt grob planen--Projekt grob planen--Projekt planen SpecIF:shows SNAP
- EP_EV_HS_1D3_Einzelprojekt-HS--Projekt realisieren--Projekt grob planen--Projekt grob planen--Projekt planen SpecIF:shows Forking Parallel Gateway
- EP_EV_HS_1D3_Einzelprojekt-HS--Projekt realisieren--Projekt grob planen--Projekt grob planen--Projekt planen SpecIF:shows Projekt initial aufgesetzt
- EP_EV_HS_1D3_Einzelprojekt-HS--Projekt realisieren--Projekt grob planen--Projekt grob planen--Projekt planen SpecIF:shows 48:Entwurfsplanung
- EP_EV_HS_1D3_Einzelprojekt-HS--Projekt realisieren--Projekt grob planen--Projekt grob planen--Projekt planen SpecIF:shows 49:Leistungen konkretisieren
- EP_EV_HS_1D3_Einzelprojekt-HS--Projekt realisieren--Projekt grob planen--Projekt grob planen--Projekt planen SpecIF:shows 50:Entwurfsplanung
- EP_EV_HS_1D3_Einzelprojekt-HS--Projekt realisieren--Projekt grob planen--Projekt grob planen--Projekt planen SpecIF:shows 52:Vergabeeinheiten erstellen
- EP_EV_HS_1D3_Einzelprojekt-HS--Projekt realisieren--Projekt grob planen--Projekt grob planen--Projekt planen SpecIF:shows 53:Leistungspositionen den Vergabeeinheiten zuordnen
- EP_EV_HS_1D3_Einzelprojekt-HS--Projekt realisieren--Projekt grob planen--Projekt grob planen--Projekt planen SpecIF:shows 55:Voraussichtliche Beschaffungsdauer ermitteln
- EP_EV_HS_1D3_Einzelprojekt-HS--Projekt realisieren--Projekt grob planen--Projekt grob planen--Projekt planen SpecIF:shows 54:Zahlungsbedingung pro Vergabeeinheit definieren
- EP_EV_HS_1D3_Einzelprojekt-HS--Projekt realisieren--Projekt grob planen--Projekt grob planen--Projekt planen SpecIF:shows 57:Grobplanung erstellen
- EP_EV_HS_1D3_Einzelprojekt-HS--Projekt realisieren--Projekt grob planen--Projekt grob planen--Projekt planen SpecIF:shows Forking Parallel Gateway
- EP_EV_HS_1D3_Einzelprojekt-HS--Projekt realisieren--Projekt grob planen--Projekt grob planen--Projekt planen SpecIF:shows Joining Parallel Gateway
- EP_EV_HS_1D3_Einzelprojekt-HS--Projekt realisieren--Projekt grob planen--Projekt grob planen--Projekt planen SpecIF:shows Forking Exclusive Gateway: Genehmigungsplanung erforderlich?
- EP_EV_HS_1D3_Einzelprojekt-HS--Projekt realisieren--Projekt grob planen--Projekt grob planen--Projekt planen SpecIF:shows Joining Exclusive Gateway
- EP_EV_HS_1D3_Einzelprojekt-HS--Projekt realisieren--Projekt grob planen--Projekt grob planen--Projekt planen SpecIF:shows Joining Parallel Gateway
- EP_EV_HS_1D3_Einzelprojekt-HS--Projekt realisieren--Projekt grob planen--Projekt grob planen--Projekt planen SpecIF:shows 51:Genehmigungsplanung
- EP_EV_HS_1D3_Einzelprojekt-HS--Projekt realisieren--Projekt grob planen--Projekt grob planen--Projekt planen SpecIF:shows Grobplanung erstellt
- EP_EV_HS_1D3_Einzelprojekt-HS--Projekt realisieren--Projekt grob planen--Projekt grob planen--Projekt planen SpecIF:shows 56:TP-Grobplanung erstellen
- EP_EV_HS_1D3_Einzelprojekt-HS--Projekt realisieren--Projekt grob planen--Projekt grob planen--Projekt planen SpecIF:shows Nein
- EP_EV_HS_1D3_Einzelprojekt-HS--Projekt realisieren--Projekt grob planen--Projekt grob planen--Projekt planen SpecIF:shows Ja
- HS Einzelprojekt - Projekt realisieren - Projekt fein planen SpecIF:contains Asset Service - Projektleitung
- HS Einzelprojekt - Projekt realisieren - Projekt fein planen SpecIF:contains Asset Service - Teilprojektleiter (Hoch- und Tiefbau, Kabelbau, Anlagenbau)
- Grobplanung abgeschlossen SpecIF:writes Projektakte - Grobplanung
- Asset Service - Teilprojektleiter (Hoch- und Tiefbau, Kabelbau, Anlagenbau) SpecIF:contains Grobplanung abgeschlossen
- 61:Leistungsverzeichnisse in Vergabeeinheiten bündeln SpecIF:reads Ausschreibungsunterlagen
- 61:Leistungsverzeichnisse in Vergabeeinheiten bündeln SpecIF:writes Ausschreibungsunterlagen
- Asset Service - Projektleitung SpecIF:contains 61:Leistungsverzeichnisse in Vergabeeinheiten bündeln
- 62:Beschaffung begleiten und bei Vergabe mitwirken SpecIF:reads SAP
- 62:Beschaffung begleiten und bei Vergabe mitwirken SpecIF:reads AVA
- 62:Beschaffung begleiten und bei Vergabe mitwirken SpecIF:reads Ausschreibungsunterlagen
- 62:Beschaffung begleiten und bei Vergabe mitwirken SpecIF:writes SAP
- 62:Beschaffung begleiten und bei Vergabe mitwirken SpecIF:writes AVA
- 62:Beschaffung begleiten und bei Vergabe mitwirken SpecIF:writes Projektakte - Feinplanung [nach Bestellung]
- Asset Service - Projektleitung SpecIF:contains 62:Beschaffung begleiten und bei Vergabe mitwirken
- Asset Service - Projektleitung SpecIF:contains Alle Ausschreibungsunterlagen (Teilprojekte) der Vergabeeinheit liegen vor
- 63:Ausführungsplan für funktionale VEs ergänzen SpecIF:reads Projektakte - Feinplanung [nach Bestellung]
- 63:Ausführungsplan für funktionale VEs ergänzen SpecIF:writes Projektakte - Feinplanung [final]
- 63:Ausführungsplan für funktionale VEs ergänzen SpecIF:writes Baustellendokumentation [erstellt]
- Asset Service - Projektleitung SpecIF:contains 63:Ausführungsplan für funktionale VEs ergänzen
- Feinplanung abgeschlossen SpecIF:reads Projektakte - Feinplanung [final]
- Asset Service - Projektleitung SpecIF:contains Feinplanung abgeschlossen
- 60:Beschaffung begleiten und bei Vergabe mitwirken SpecIF:reads SAP
- 60:Beschaffung begleiten und bei Vergabe mitwirken SpecIF:reads AVA
- 60:Beschaffung begleiten und bei Vergabe mitwirken SpecIF:reads Projektakte - Feinplanung
- 60:Beschaffung begleiten und bei Vergabe mitwirken SpecIF:reads Ausschreibungsunterlagen
- 60:Beschaffung begleiten und bei Vergabe mitwirken SpecIF:writes SAP
- 60:Beschaffung begleiten und bei Vergabe mitwirken SpecIF:writes AVA
- 60:Beschaffung begleiten und bei Vergabe mitwirken SpecIF:writes Projektakte - Feinplanung [nach Bestellung]
- Asset Service - Teilprojektleiter (Hoch- und Tiefbau, Kabelbau, Anlagenbau) SpecIF:contains 60:Beschaffung begleiten und bei Vergabe mitwirken
- subProcess_460817227 SpecIF:contains startEvent
- 58:Ausführungsplanung erstellen SpecIF:reads Projektakte - Grobplanung
- 58:Ausführungsplanung erstellen SpecIF:writes Projektakte - Feinplanung
- subProcess_460817227 SpecIF:contains 58:Ausführungsplanung erstellen
- 59:Vergabe vorbereiten SpecIF:reads Projektakte - Feinplanung
- 59:Vergabe vorbereiten SpecIF:reads SAP
- 59:Vergabe vorbereiten SpecIF:reads AVA
- 59:Vergabe vorbereiten SpecIF:writes AVA
- 59:Vergabe vorbereiten SpecIF:writes SAP
- 59:Vergabe vorbereiten SpecIF:writes Ausschreibungsunterlagen
- subProcess_460817227 SpecIF:contains 59:Vergabe vorbereiten
- subProcess_460817227 SpecIF:contains endEvent
- Forking Exclusive Gateway: Funktionale Ausschreibung? SpecIF:signals Nein
- Nein SpecIF:triggers 58:Ausführungsplanung erstellen
- 58:Ausführungsplanung erstellen SpecIF:precedes Joining Exclusive Gateway
- Joining Exclusive Gateway SpecIF:precedes 59:Vergabe vorbereiten
- Forking Exclusive Gateway: Funktionale Ausschreibung? SpecIF:signals Ja
- Ja SpecIF:triggers Joining Exclusive Gateway
- 59:Vergabe vorbereiten SpecIF:signals endEvent
- startEvent SpecIF:triggers Forking Exclusive Gateway: Funktionale Ausschreibung?
- subProcess_460817227 SpecIF:reads Projektakte - Grobplanung
- Asset Service - Teilprojektleiter (Hoch- und Tiefbau, Kabelbau, Anlagenbau) SpecIF:contains subProcess_460817227
- Grobplanung abgeschlossen SpecIF:triggers subProcess_460817227
- Alle Ausschreibungsunterlagen (Teilprojekte) der Vergabeeinheit liegen vor SpecIF:triggers 61:Leistungsverzeichnisse in Vergabeeinheiten bündeln
- 61:Leistungsverzeichnisse in Vergabeeinheiten bündeln SpecIF:precedes 62:Beschaffung begleiten und bei Vergabe mitwirken
- 62:Beschaffung begleiten und bei Vergabe mitwirken SpecIF:precedes Joining Exclusive Gateway
- Forking Exclusive Gateway: TP-Ausschreibungsunterlage Teil des Hauptauftragnehmers? SpecIF:signals Ja
- Ja SpecIF:triggers Alle Ausschreibungsunterlagen (Teilprojekte) der Vergabeeinheit liegen vor
- Forking Exclusive Gateway: Funktionale Ausschreibung vorhanden? SpecIF:signals Ja
- Ja SpecIF:triggers 63:Ausführungsplan für funktionale VEs ergänzen
- 63:Ausführungsplan für funktionale VEs ergänzen SpecIF:precedes Joining Exclusive Gateway
- Joining Exclusive Gateway SpecIF:signals Feinplanung abgeschlossen
- Forking Exclusive Gateway: Funktionale Ausschreibung vorhanden? SpecIF:signals Nein
- Nein SpecIF:triggers Joining Exclusive Gateway
- Joining Exclusive Gateway SpecIF:precedes Forking Exclusive Gateway: Funktionale Ausschreibung vorhanden?
- 60:Beschaffung begleiten und bei Vergabe mitwirken SpecIF:precedes Joining Exclusive Gateway
- Forking Exclusive Gateway: TP-Ausschreibungsunterlage Teil des Hauptauftragnehmers? SpecIF:signals Nein
- Nein SpecIF:triggers 60:Beschaffung begleiten und bei Vergabe mitwirken
- subProcess_460817227 SpecIF:precedes Forking Exclusive Gateway: TP-Ausschreibungsunterlage Teil des Hauptauftragnehmers?
- Text Annotation 01 SpecIF:refersTo Projektakte - Feinplanung
- Text Annotation 03 SpecIF:refersTo 59:Vergabe vorbereiten
- Text Annotation 07 SpecIF:refersTo Forking Exclusive Gateway: Funktionale Ausschreibung?
- Text Annotation 02 SpecIF:refersTo Ausschreibungsunterlagen
- Text Annotation 05 SpecIF:refersTo Feinplanung abgeschlossen
- Text Annotation 06 SpecIF:refersTo subProcess_460817227
- Text Annotation 08 SpecIF:refersTo Projektakte - Feinplanung [nach Bestellung]
- Text Annotation 04 SpecIF:refersTo Projektakte - Feinplanung [final]
- Text Annotation 09 SpecIF:refersTo 59:Vergabe vorbereiten
- Text Annotation 10 SpecIF:refersTo 59:Vergabe vorbereiten
- EP_EV_HS_1D4_Einzelprojekt-HS--Projekt realisieren--Projekt fein planen SpecIF:shows HS Einzelprojekt - Projekt realisieren - Projekt fein planen
- EP_EV_HS_1D4_Einzelprojekt-HS--Projekt realisieren--Projekt fein planen SpecIF:shows Asset Service - Projektleitung
- EP_EV_HS_1D4_Einzelprojekt-HS--Projekt realisieren--Projekt fein planen SpecIF:shows Asset Service - Teilprojektleiter (Hoch- und Tiefbau, Kabelbau, Anlagenbau)
- EP_EV_HS_1D4_Einzelprojekt-HS--Projekt realisieren--Projekt fein planen SpecIF:shows Projektakte - Grobplanung
- EP_EV_HS_1D4_Einzelprojekt-HS--Projekt realisieren--Projekt fein planen SpecIF:shows Projektakte - Feinplanung [nach Bestellung]
- EP_EV_HS_1D4_Einzelprojekt-HS--Projekt realisieren--Projekt fein planen SpecIF:shows AVA
- EP_EV_HS_1D4_Einzelprojekt-HS--Projekt realisieren--Projekt fein planen SpecIF:shows SAP
- EP_EV_HS_1D4_Einzelprojekt-HS--Projekt realisieren--Projekt fein planen SpecIF:shows Baustellendokumentation [erstellt]
- EP_EV_HS_1D4_Einzelprojekt-HS--Projekt realisieren--Projekt fein planen SpecIF:shows Projektakte - Feinplanung [final]
- EP_EV_HS_1D4_Einzelprojekt-HS--Projekt realisieren--Projekt fein planen SpecIF:shows Projektakte - Feinplanung
- EP_EV_HS_1D4_Einzelprojekt-HS--Projekt realisieren--Projekt fein planen SpecIF:shows Ausschreibungsunterlagen
- EP_EV_HS_1D4_Einzelprojekt-HS--Projekt realisieren--Projekt fein planen SpecIF:shows Grobplanung abgeschlossen
- EP_EV_HS_1D4_Einzelprojekt-HS--Projekt realisieren--Projekt fein planen SpecIF:shows 61:Leistungsverzeichnisse in Vergabeeinheiten bündeln
- EP_EV_HS_1D4_Einzelprojekt-HS--Projekt realisieren--Projekt fein planen SpecIF:shows 62:Beschaffung begleiten und bei Vergabe mitwirken
- EP_EV_HS_1D4_Einzelprojekt-HS--Projekt realisieren--Projekt fein planen SpecIF:shows Alle Ausschreibungsunterlagen (Teilprojekte) der Vergabeeinheit liegen vor
- EP_EV_HS_1D4_Einzelprojekt-HS--Projekt realisieren--Projekt fein planen SpecIF:shows 63:Ausführungsplan für funktionale VEs ergänzen
- EP_EV_HS_1D4_Einzelprojekt-HS--Projekt realisieren--Projekt fein planen SpecIF:shows Feinplanung abgeschlossen
- EP_EV_HS_1D4_Einzelprojekt-HS--Projekt realisieren--Projekt fein planen SpecIF:shows Joining Exclusive Gateway
- EP_EV_HS_1D4_Einzelprojekt-HS--Projekt realisieren--Projekt fein planen SpecIF:shows Forking Exclusive Gateway: Funktionale Ausschreibung vorhanden?
- EP_EV_HS_1D4_Einzelprojekt-HS--Projekt realisieren--Projekt fein planen SpecIF:shows Joining Exclusive Gateway
- EP_EV_HS_1D4_Einzelprojekt-HS--Projekt realisieren--Projekt fein planen SpecIF:shows 60:Beschaffung begleiten und bei Vergabe mitwirken
- EP_EV_HS_1D4_Einzelprojekt-HS--Projekt realisieren--Projekt fein planen SpecIF:shows Forking Exclusive Gateway: TP-Ausschreibungsunterlage Teil des Hauptauftragnehmers?
- EP_EV_HS_1D4_Einzelprojekt-HS--Projekt realisieren--Projekt fein planen SpecIF:shows subProcess_460817227
- EP_EV_HS_1D4_Einzelprojekt-HS--Projekt realisieren--Projekt fein planen SpecIF:shows startEvent
- EP_EV_HS_1D4_Einzelprojekt-HS--Projekt realisieren--Projekt fein planen SpecIF:shows 58:Ausführungsplanung erstellen
- EP_EV_HS_1D4_Einzelprojekt-HS--Projekt realisieren--Projekt fein planen SpecIF:shows 59:Vergabe vorbereiten
- EP_EV_HS_1D4_Einzelprojekt-HS--Projekt realisieren--Projekt fein planen SpecIF:shows Joining Exclusive Gateway
- EP_EV_HS_1D4_Einzelprojekt-HS--Projekt realisieren--Projekt fein planen SpecIF:shows endEvent
- EP_EV_HS_1D4_Einzelprojekt-HS--Projekt realisieren--Projekt fein planen SpecIF:shows Forking Exclusive Gateway: Funktionale Ausschreibung?
- EP_EV_HS_1D4_Einzelprojekt-HS--Projekt realisieren--Projekt fein planen SpecIF:shows Nein
- EP_EV_HS_1D4_Einzelprojekt-HS--Projekt realisieren--Projekt fein planen SpecIF:shows Ja
- EP_EV_HS_1D4_Einzelprojekt-HS--Projekt realisieren--Projekt fein planen SpecIF:shows Ja
- EP_EV_HS_1D4_Einzelprojekt-HS--Projekt realisieren--Projekt fein planen SpecIF:shows Ja
- EP_EV_HS_1D4_Einzelprojekt-HS--Projekt realisieren--Projekt fein planen SpecIF:shows Nein
- EP_EV_HS_1D4_Einzelprojekt-HS--Projekt realisieren--Projekt fein planen SpecIF:shows Nein
- HS Einzelprojekt - Projekt realisieren - Projekt ausführen SpecIF:contains Asset Service - Projektleitung
- HS Einzelprojekt - Projekt realisieren - Projekt ausführen SpecIF:contains Asset Service - Bauführer
- HS Einzelprojekt - Projekt realisieren - Projekt ausführen SpecIF:contains Asset Service - Teilprojektleitung (Hoch- und Tiefbau, Kabelbau, Anlagenbau)
- 64:Werksprüfung durchführen SpecIF:reads Projektakte - Feinplanung [final]
- 64:Werksprüfung durchführen SpecIF:writes Baustellendokumentation [kommentiert]
- 64:Werksprüfung durchführen SpecIF:writes Werksprüfungsprotokoll
- 64:Werksprüfung durchführen SpecIF:writes Restpunktliste
- Asset Service - Teilprojektleitung (Hoch- und Tiefbau, Kabelbau, Anlagenbau) SpecIF:contains 64:Werksprüfung durchführen
- Feinplanung abgeschlossen und zur Ausführung freigegeben SpecIF:writes Projektakte - Feinplanung [final]
- Asset Service - Teilprojektleitung (Hoch- und Tiefbau, Kabelbau, Anlagenbau) SpecIF:contains Feinplanung abgeschlossen und zur Ausführung freigegeben
- 65:Bauüberwachung durchführen SpecIF:reads Projektakte - Feinplanung [final]
- 65:Bauüberwachung durchführen SpecIF:reads Restpunktliste
- 65:Bauüberwachung durchführen SpecIF:reads Terminplan [live]
- 65:Bauüberwachung durchführen SpecIF:reads Aufmaß Leistungspositionen
- 65:Bauüberwachung durchführen SpecIF:reads SNAP (AVA?)
- 65:Bauüberwachung durchführen SpecIF:writes FFM
- 65:Bauüberwachung durchführen SpecIF:writes Leistungsbestätigungs-Dokumente
- 65:Bauüberwachung durchführen SpecIF:writes Protokoll Baubesprechung
- 65:Bauüberwachung durchführen SpecIF:writes Projektakte - Feinplanung [Bauführer]
- 65:Bauüberwachung durchführen SpecIF:writes Terminplan [live]
- 65:Bauüberwachung durchführen SpecIF:writes Restpunktliste
- 65:Bauüberwachung durchführen SpecIF:writes SNAP (AVA?)
- Asset Service - Bauführer SpecIF:contains 65:Bauüberwachung durchführen
- 67:Abnahme der Vergabeeinheiten durchführen SpecIF:reads Restpunktliste
- 67:Abnahme der Vergabeeinheiten durchführen SpecIF:writes Abnahmeprotokoll
- Asset Service - Projektleitung SpecIF:contains 67:Abnahme der Vergabeeinheiten durchführen
- 68:Endabrechnung und Projektabschluss durchführen SpecIF:reads Vertrag Auftragnehmer (AN)
- 68:Endabrechnung und Projektabschluss durchführen SpecIF:reads Leistungsbestätigungs-Dokumente
- 68:Endabrechnung und Projektabschluss durchführen SpecIF:writes Prognose: PUP, PAM, PLC
- 68:Endabrechnung und Projektabschluss durchführen SpecIF:writes SAP PID
- 68:Endabrechnung und Projektabschluss durchführen SpecIF:writes AVA
- Asset Service - Projektleitung SpecIF:contains 68:Endabrechnung und Projektabschluss durchführen
- technische Fertigmeldungen aller TPs in SAP SpecIF:reads Technische Fertigmeldungen
- Asset Service - Projektleitung SpecIF:contains technische Fertigmeldungen aller TPs in SAP
- Projekt ist technisch fertig gemeldet SpecIF:reads Projektakte - Dokumentation
- Projekt ist technisch fertig gemeldet SpecIF:reads Technische Fertigmeldungen
- Asset Service - Projektleitung SpecIF:contains Projekt ist technisch fertig gemeldet
- 66:Dokumentation erstellen SpecIF:reads Baustellendokumentation [kommentiert]
- 66:Dokumentation erstellen SpecIF:reads Betriebsmitteldaten
- 66:Dokumentation erstellen SpecIF:writes Enddokumentation
- 66:Dokumentation erstellen SpecIF:writes Projektakte - Dokumentation
- 66:Dokumentation erstellen SpecIF:writes SAP
- Asset Service - Teilprojektleitung (Hoch- und Tiefbau, Kabelbau, Anlagenbau) SpecIF:contains 66:Dokumentation erstellen
- 69:Lessons Learned übertragen SpecIF:reads SAP
- 69:Lessons Learned übertragen SpecIF:writes AVA
- Asset Service - Projektleitung SpecIF:contains 69:Lessons Learned übertragen
- Asset Service - Bauführer SpecIF:contains Inbetriebnahme/Funktionsnachweis durchgeführt
- 66:Dokumentation erstellen SpecIF:precedes Joining Parallel Gateway
- 67:Abnahme der Vergabeeinheiten durchführen SpecIF:precedes Joining Parallel Gateway
- Joining Parallel Gateway SpecIF:precedes 68:Endabrechnung und Projektabschluss durchführen
- Forking Parallel Gateway SpecIF:precedes 67:Abnahme der Vergabeeinheiten durchführen
- 68:Endabrechnung und Projektabschluss durchführen SpecIF:signals technische Fertigmeldungen aller TPs in SAP
- technische Fertigmeldungen aller TPs in SAP SpecIF:triggers 69:Lessons Learned übertragen
- 69:Lessons Learned übertragen SpecIF:signals Projekt ist technisch fertig gemeldet
- Feinplanung abgeschlossen und zur Ausführung freigegeben SpecIF:triggers Forking Exclusive Gateway: Vorfertigung im Werk
- Forking Exclusive Gateway: Vorfertigung im Werk SpecIF:signals Nein
- Nein SpecIF:triggers Joining Exclusive Gateway
- Forking Exclusive Gateway: Vorfertigung im Werk SpecIF:signals Ja
- Ja SpecIF:triggers 64:Werksprüfung durchführen
- 64:Werksprüfung durchführen SpecIF:precedes Joining Exclusive Gateway
- Joining Exclusive Gateway SpecIF:precedes 65:Bauüberwachung durchführen
- Forking Parallel Gateway SpecIF:precedes 66:Dokumentation erstellen
- Inbetriebnahme/Funktionsnachweis durchgeführt SpecIF:triggers Forking Parallel Gateway
- 65:Bauüberwachung durchführen SpecIF:signals Inbetriebnahme/Funktionsnachweis durchgeführt
- Text Annotation 01 SpecIF:refersTo Baustellendokumentation [kommentiert]
- Text Annotation 03 SpecIF:refersTo Abnahmeprotokoll
- Text Annotation 04 SpecIF:refersTo Betriebsmitteldaten
- Text Annotation 05 SpecIF:refersTo 69:Lessons Learned übertragen
- Text Annotation 06 SpecIF:refersTo Leistungsbestätigungs-Dokumente
- Text Annotation 07 SpecIF:refersTo 65:Bauüberwachung durchführen
- Text Annotation 08 SpecIF:refersTo Projektakte - Feinplanung [Bauführer]
- Text Annotation 09 SpecIF:refersTo 68:Endabrechnung und Projektabschluss durchführen
- EP_EV_HS_1D5_Einzelprojekt-HS--Projekt realisieren--Projekt ausführen SpecIF:shows HS Einzelprojekt - Projekt realisieren - Projekt ausführen
- EP_EV_HS_1D5_Einzelprojekt-HS--Projekt realisieren--Projekt ausführen SpecIF:shows Asset Service - Projektleitung
- EP_EV_HS_1D5_Einzelprojekt-HS--Projekt realisieren--Projekt ausführen SpecIF:shows Asset Service - Bauführer
- EP_EV_HS_1D5_Einzelprojekt-HS--Projekt realisieren--Projekt ausführen SpecIF:shows Asset Service - Teilprojektleitung (Hoch- und Tiefbau, Kabelbau, Anlagenbau)
- EP_EV_HS_1D5_Einzelprojekt-HS--Projekt realisieren--Projekt ausführen SpecIF:shows Projektakte - Feinplanung [final]
- EP_EV_HS_1D5_Einzelprojekt-HS--Projekt realisieren--Projekt ausführen SpecIF:shows Baustellendokumentation [kommentiert]
- EP_EV_HS_1D5_Einzelprojekt-HS--Projekt realisieren--Projekt ausführen SpecIF:shows Werksprüfungsprotokoll
- EP_EV_HS_1D5_Einzelprojekt-HS--Projekt realisieren--Projekt ausführen SpecIF:shows Restpunktliste
- EP_EV_HS_1D5_Einzelprojekt-HS--Projekt realisieren--Projekt ausführen SpecIF:shows FFM
- EP_EV_HS_1D5_Einzelprojekt-HS--Projekt realisieren--Projekt ausführen SpecIF:shows Leistungsbestätigungs-Dokumente
- EP_EV_HS_1D5_Einzelprojekt-HS--Projekt realisieren--Projekt ausführen SpecIF:shows Protokoll Baubesprechung
- EP_EV_HS_1D5_Einzelprojekt-HS--Projekt realisieren--Projekt ausführen SpecIF:shows Projektakte - Feinplanung [Bauführer]
- EP_EV_HS_1D5_Einzelprojekt-HS--Projekt realisieren--Projekt ausführen SpecIF:shows Terminplan [live]
- EP_EV_HS_1D5_Einzelprojekt-HS--Projekt realisieren--Projekt ausführen SpecIF:shows Abnahmeprotokoll
- EP_EV_HS_1D5_Einzelprojekt-HS--Projekt realisieren--Projekt ausführen SpecIF:shows Vertrag Auftragnehmer (AN)
- EP_EV_HS_1D5_Einzelprojekt-HS--Projekt realisieren--Projekt ausführen SpecIF:shows Prognose: PUP, PAM, PLC
- EP_EV_HS_1D5_Einzelprojekt-HS--Projekt realisieren--Projekt ausführen SpecIF:shows SAP PID
- EP_EV_HS_1D5_Einzelprojekt-HS--Projekt realisieren--Projekt ausführen SpecIF:shows AVA
- EP_EV_HS_1D5_Einzelprojekt-HS--Projekt realisieren--Projekt ausführen SpecIF:shows Technische Fertigmeldungen
- EP_EV_HS_1D5_Einzelprojekt-HS--Projekt realisieren--Projekt ausführen SpecIF:shows SAP
- EP_EV_HS_1D5_Einzelprojekt-HS--Projekt realisieren--Projekt ausführen SpecIF:shows Enddokumentation
- EP_EV_HS_1D5_Einzelprojekt-HS--Projekt realisieren--Projekt ausführen SpecIF:shows Projektakte - Dokumentation
- EP_EV_HS_1D5_Einzelprojekt-HS--Projekt realisieren--Projekt ausführen SpecIF:shows Betriebsmitteldaten
- EP_EV_HS_1D5_Einzelprojekt-HS--Projekt realisieren--Projekt ausführen SpecIF:shows SNAP (AVA?)
- EP_EV_HS_1D5_Einzelprojekt-HS--Projekt realisieren--Projekt ausführen SpecIF:shows Aufmaß Leistungspositionen
- EP_EV_HS_1D5_Einzelprojekt-HS--Projekt realisieren--Projekt ausführen SpecIF:shows Forking Exclusive Gateway: Vorfertigung im Werk
- EP_EV_HS_1D5_Einzelprojekt-HS--Projekt realisieren--Projekt ausführen SpecIF:shows 64:Werksprüfung durchführen
- EP_EV_HS_1D5_Einzelprojekt-HS--Projekt realisieren--Projekt ausführen SpecIF:shows Joining Exclusive Gateway
- EP_EV_HS_1D5_Einzelprojekt-HS--Projekt realisieren--Projekt ausführen SpecIF:shows Feinplanung abgeschlossen und zur Ausführung freigegeben
- EP_EV_HS_1D5_Einzelprojekt-HS--Projekt realisieren--Projekt ausführen SpecIF:shows 65:Bauüberwachung durchführen
- EP_EV_HS_1D5_Einzelprojekt-HS--Projekt realisieren--Projekt ausführen SpecIF:shows 67:Abnahme der Vergabeeinheiten durchführen
- EP_EV_HS_1D5_Einzelprojekt-HS--Projekt realisieren--Projekt ausführen SpecIF:shows Joining Parallel Gateway
- EP_EV_HS_1D5_Einzelprojekt-HS--Projekt realisieren--Projekt ausführen SpecIF:shows 68:Endabrechnung und Projektabschluss durchführen
- EP_EV_HS_1D5_Einzelprojekt-HS--Projekt realisieren--Projekt ausführen SpecIF:shows technische Fertigmeldungen aller TPs in SAP
- EP_EV_HS_1D5_Einzelprojekt-HS--Projekt realisieren--Projekt ausführen SpecIF:shows Projekt ist technisch fertig gemeldet
- EP_EV_HS_1D5_Einzelprojekt-HS--Projekt realisieren--Projekt ausführen SpecIF:shows 66:Dokumentation erstellen
- EP_EV_HS_1D5_Einzelprojekt-HS--Projekt realisieren--Projekt ausführen SpecIF:shows Forking Parallel Gateway
- EP_EV_HS_1D5_Einzelprojekt-HS--Projekt realisieren--Projekt ausführen SpecIF:shows 69:Lessons Learned übertragen
- EP_EV_HS_1D5_Einzelprojekt-HS--Projekt realisieren--Projekt ausführen SpecIF:shows Inbetriebnahme/Funktionsnachweis durchgeführt
- EP_EV_HS_1D5_Einzelprojekt-HS--Projekt realisieren--Projekt ausführen SpecIF:shows Nein
- EP_EV_HS_1D5_Einzelprojekt-HS--Projekt realisieren--Projekt ausführen SpecIF:shows Ja
- HS Einzelprojekt - Projekt realisieren - Projekt fein planen - Beschaffung SpecIF:contains Anforderer
- HS Einzelprojekt - Projekt realisieren - Projekt fein planen - Beschaffung SpecIF:contains Einkauf
- 71:Beschaffungsprozess SpecIF:reads SAP (BANF)
- 71:Beschaffungsprozess SpecIF:reads AVA
- 71:Beschaffungsprozess SpecIF:writes Vertrag Auftragnehmer (AN)
- 71:Beschaffungsprozess SpecIF:writes SAP (BANF)
- 71:Beschaffungsprozess SpecIF:writes AVA
- Einkauf SpecIF:contains 71:Beschaffungsprozess
- 72:Bestellungen durchführen SpecIF:reads Vertrag Auftragnehmer (AN)
- 72:Bestellungen durchführen SpecIF:writes SAP
- 72:Bestellungen durchführen SpecIF:writes AVA
- 72:Bestellungen durchführen SpecIF:writes Projektakte - Feinplanung
- Einkauf SpecIF:contains 72:Bestellungen durchführen
- 70:Vergabeeinheit aus Liste auswählen und BANFen erstellen SpecIF:reads AVA
- 70:Vergabeeinheit aus Liste auswählen und BANFen erstellen SpecIF:reads Ausschreibungsunterlagen
- 70:Vergabeeinheit aus Liste auswählen und BANFen erstellen SpecIF:writes SAP (BANF)
- Anforderer SpecIF:contains 70:Vergabeeinheit aus Liste auswählen und BANFen erstellen
- Anforderer SpecIF:contains Ausschreibungsunterlagen liegen vor
- Anforderer SpecIF:contains BANF freigegeben
- Einkauf SpecIF:contains Bestellung für VE erfolgt
- VE SpecIF:reads Vergabeentscheidung
- Einkauf SpecIF:contains VE
- 72:Bestellungen durchführen SpecIF:signals Bestellung für VE erfolgt
- 70:Vergabeeinheit aus Liste auswählen und BANFen erstellen SpecIF:signals BANF freigegeben
- VE SpecIF:triggers 72:Bestellungen durchführen
- 71:Beschaffungsprozess SpecIF:signals VE
- BANF freigegeben SpecIF:triggers 71:Beschaffungsprozess
- Ausschreibungsunterlagen liegen vor SpecIF:triggers 70:Vergabeeinheit aus Liste auswählen und BANFen erstellen
- Text Annotation 01 SpecIF:refersTo 70:Vergabeeinheit aus Liste auswählen und BANFen erstellen
- Text Annotation 02 SpecIF:refersTo 71:Beschaffungsprozess
- Text Annotation 04 SpecIF:refersTo SAP (BANF)
- Text Annotation 03 SpecIF:refersTo Vertrag Auftragnehmer (AN)
- Text Annotation 05 SpecIF:refersTo Vertrag Auftragnehmer (AN)
- Text Annotation 06 SpecIF:refersTo 72:Bestellungen durchführen
- EP_EV_HS_1D6_Einzelprojekt-HS--Projekt realisieren--Beschaffung SpecIF:shows HS Einzelprojekt - Projekt realisieren - Projekt fein planen - Beschaffung
- EP_EV_HS_1D6_Einzelprojekt-HS--Projekt realisieren--Beschaffung SpecIF:shows Anforderer
- EP_EV_HS_1D6_Einzelprojekt-HS--Projekt realisieren--Beschaffung SpecIF:shows Einkauf
- EP_EV_HS_1D6_Einzelprojekt-HS--Projekt realisieren--Beschaffung SpecIF:shows SAP (BANF)
- EP_EV_HS_1D6_Einzelprojekt-HS--Projekt realisieren--Beschaffung SpecIF:shows AVA
- EP_EV_HS_1D6_Einzelprojekt-HS--Projekt realisieren--Beschaffung SpecIF:shows Vertrag Auftragnehmer (AN)
- EP_EV_HS_1D6_Einzelprojekt-HS--Projekt realisieren--Beschaffung SpecIF:shows Vergabeentscheidung
- EP_EV_HS_1D6_Einzelprojekt-HS--Projekt realisieren--Beschaffung SpecIF:shows Projektakte - Feinplanung
- EP_EV_HS_1D6_Einzelprojekt-HS--Projekt realisieren--Beschaffung SpecIF:shows SAP
- EP_EV_HS_1D6_Einzelprojekt-HS--Projekt realisieren--Beschaffung SpecIF:shows Ausschreibungsunterlagen
- EP_EV_HS_1D6_Einzelprojekt-HS--Projekt realisieren--Beschaffung SpecIF:shows 71:Beschaffungsprozess
- EP_EV_HS_1D6_Einzelprojekt-HS--Projekt realisieren--Beschaffung SpecIF:shows 72:Bestellungen durchführen
- EP_EV_HS_1D6_Einzelprojekt-HS--Projekt realisieren--Beschaffung SpecIF:shows 70:Vergabeeinheit aus Liste auswählen und BANFen erstellen
- EP_EV_HS_1D6_Einzelprojekt-HS--Projekt realisieren--Beschaffung SpecIF:shows Ausschreibungsunterlagen liegen vor
- EP_EV_HS_1D6_Einzelprojekt-HS--Projekt realisieren--Beschaffung SpecIF:shows BANF freigegeben
- EP_EV_HS_1D6_Einzelprojekt-HS--Projekt realisieren--Beschaffung SpecIF:shows Bestellung für VE erfolgt
- EP_EV_HS_1D6_Einzelprojekt-HS--Projekt realisieren--Beschaffung SpecIF:shows VE
- HS Einzelprojekt -- Planungsrunde durchführen SpecIF:contains Asset Service
- Asset Service SpecIF:contains Planungsrunde steht an
- Asset Service SpecIF:contains Planungsrunde abgeschlossen
- 73:Protokoll erstellen SpecIF:reads Projektakte
- 73:Protokoll erstellen SpecIF:writes Protokoll Planungsrunde
- Asset Service SpecIF:contains 73:Protokoll erstellen
- 74:Dokumentation anpassen SpecIF:reads Projektakte
- 74:Dokumentation anpassen SpecIF:writes Projektakte
- Asset Service SpecIF:contains 74:Dokumentation anpassen
- Asset Service SpecIF:contains 75:Neu generierte ToDos verteilen
- 75:Neu generierte ToDos verteilen SpecIF:signals Planungsrunde abgeschlossen
- 73:Protokoll erstellen SpecIF:precedes 74:Dokumentation anpassen
- 74:Dokumentation anpassen SpecIF:precedes 75:Neu generierte ToDos verteilen
- Planungsrunde steht an SpecIF:triggers 73:Protokoll erstellen
- Text Annotation 01 SpecIF:refersTo Projektakte
- EP_EV_HS_1D7_Einzelprojekt-HS--Projekt realisieren--Planungsrunde durchführen SpecIF:shows HS Einzelprojekt -- Planungsrunde durchführen
- EP_EV_HS_1D7_Einzelprojekt-HS--Projekt realisieren--Planungsrunde durchführen SpecIF:shows Asset Service
- EP_EV_HS_1D7_Einzelprojekt-HS--Projekt realisieren--Planungsrunde durchführen SpecIF:shows Protokoll Planungsrunde
- EP_EV_HS_1D7_Einzelprojekt-HS--Projekt realisieren--Planungsrunde durchführen SpecIF:shows Projektakte
- EP_EV_HS_1D7_Einzelprojekt-HS--Projekt realisieren--Planungsrunde durchführen SpecIF:shows Planungsrunde steht an
- EP_EV_HS_1D7_Einzelprojekt-HS--Projekt realisieren--Planungsrunde durchführen SpecIF:shows Planungsrunde abgeschlossen
- EP_EV_HS_1D7_Einzelprojekt-HS--Projekt realisieren--Planungsrunde durchführen SpecIF:shows 73:Protokoll erstellen
- EP_EV_HS_1D7_Einzelprojekt-HS--Projekt realisieren--Planungsrunde durchführen SpecIF:shows 74:Dokumentation anpassen
- EP_EV_HS_1D7_Einzelprojekt-HS--Projekt realisieren--Planungsrunde durchführen SpecIF:shows 75:Neu generierte ToDos verteilen
- Sammelprojekt-MS/NS--Netzauftrag konzipieren, planen und ausführen SpecIF:contains Asset Service - Stationsbau
- Sammelprojekt-MS/NS--Netzauftrag konzipieren, planen und ausführen SpecIF:contains Asset Service
- Kundenanfrage eingegangen SpecIF:writes Kundenanfrage [initial]
- Asset Service SpecIF:contains Kundenanfrage eingegangen
- 1:HA durchführen / Netzauftrag konzipieren SpecIF:reads Kundenanfrage [initial]
- 1:HA durchführen / Netzauftrag konzipieren SpecIF:writes Technisches Konzept [final konzipiert]
- Asset Service SpecIF:contains 1:HA durchführen / Netzauftrag konzipieren
- 2:Netzauftrag SKB konzipieren SpecIF:reads Kundenanfrage [initial]
- 2:Netzauftrag SKB konzipieren SpecIF:writes Technisches Konzept [final konzipiert]
- Asset Service SpecIF:contains 2:Netzauftrag SKB konzipieren
- 3:Netzauftrag planen SpecIF:reads Technisches Konzept [final konzipiert]
- 3:Netzauftrag planen SpecIF:writes Bauakte
- Asset Service SpecIF:contains 3:Netzauftrag planen
- 4:Stationsbau planen SpecIF:reads SAP (NeMo)
- 4:Stationsbau planen SpecIF:reads Technisches Konzept [final konzipiert]
- 4:Stationsbau planen SpecIF:writes Stationszeichnung
- 4:Stationsbau planen SpecIF:writes Stationsbauauftrag
- Asset Service - Stationsbau SpecIF:contains 4:Stationsbau planen
- 5:Stationsbau ausführen SpecIF:reads Stationszeichnung
- 5:Stationsbau ausführen SpecIF:reads SAP (NeMo)
- 5:Stationsbau ausführen SpecIF:reads Technisches Konzept [final konzipiert]
- 5:Stationsbau ausführen SpecIF:reads Stationsbauauftrag
- 5:Stationsbau ausführen SpecIF:writes SAP (NeMo)
- Asset Service - Stationsbau SpecIF:contains 5:Stationsbau ausführen
- 6:Netzauftrag ausführen SpecIF:reads Bauakte
- 6:Netzauftrag ausführen SpecIF:writes Leistungserfassungsblatt [bestätigt]
- 6:Netzauftrag ausführen SpecIF:writes Bauakte [abgeschlossen]
- Asset Service SpecIF:contains 6:Netzauftrag ausführen
- Asset Service SpecIF:contains Projekt in Betrieb überführt
- Asset Service SpecIF:contains 7:Netzauftrag in Betrieb überführen
- Forking Exclusive Gateway: Art der Kundenanfrage? SpecIF:signals Kundenanfrage Niederspannung
- Kundenanfrage Niederspannung SpecIF:triggers 1:HA durchführen / Netzauftrag konzipieren
- Kundenanfrage eingegangen SpecIF:triggers Forking Exclusive Gateway: Art der Kundenanfrage?
- Forking Exclusive Gateway: Art der Kundenanfrage? SpecIF:signals Mittelspannung 10kV (>2MVA)
- Mittelspannung 10kV (>2MVA) SpecIF:triggers 2:Netzauftrag SKB konzipieren
- 1:HA durchführen / Netzauftrag konzipieren SpecIF:precedes Joining Exclusive Gateway
- 2:Netzauftrag SKB konzipieren SpecIF:precedes Joining Exclusive Gateway
- Joining Exclusive Gateway SpecIF:precedes Forking Parallel Gateway
- Forking Exclusive Gateway: Stationsbau erforderlich? SpecIF:signals Ja
- Ja SpecIF:triggers 4:Stationsbau planen
- Forking Parallel Gateway SpecIF:precedes Forking Exclusive Gateway: Stationsbau erforderlich?
- Forking Parallel Gateway SpecIF:precedes 3:Netzauftrag planen
- Forking Exclusive Gateway: Stationsbau erforderlich? SpecIF:signals Nein
- Nein SpecIF:triggers Joining Exclusive Gateway
- 3:Netzauftrag planen SpecIF:precedes Joining Parallel Gateway
- 4:Stationsbau planen SpecIF:precedes 5:Stationsbau ausführen
- 5:Stationsbau ausführen SpecIF:precedes Joining Exclusive Gateway
- Joining Exclusive Gateway SpecIF:precedes Joining Parallel Gateway
- Joining Parallel Gateway SpecIF:precedes 6:Netzauftrag ausführen
- 6:Netzauftrag ausführen SpecIF:precedes 7:Netzauftrag in Betrieb überführen
- 7:Netzauftrag in Betrieb überführen SpecIF:signals Projekt in Betrieb überführt
- SP_KV_MSNS_2_Sammelprojekt-MSNS--Netzauftrag konzipieren, planen und ausführen SpecIF:shows Sammelprojekt-MS/NS--Netzauftrag konzipieren, planen und ausführen
- SP_KV_MSNS_2_Sammelprojekt-MSNS--Netzauftrag konzipieren, planen und ausführen SpecIF:shows Asset Service - Stationsbau
- SP_KV_MSNS_2_Sammelprojekt-MSNS--Netzauftrag konzipieren, planen und ausführen SpecIF:shows Asset Service
- SP_KV_MSNS_2_Sammelprojekt-MSNS--Netzauftrag konzipieren, planen und ausführen SpecIF:shows Technisches Konzept [final konzipiert]
- SP_KV_MSNS_2_Sammelprojekt-MSNS--Netzauftrag konzipieren, planen und ausführen SpecIF:shows Kundenanfrage [initial]
- SP_KV_MSNS_2_Sammelprojekt-MSNS--Netzauftrag konzipieren, planen und ausführen SpecIF:shows SAP (NeMo)
- SP_KV_MSNS_2_Sammelprojekt-MSNS--Netzauftrag konzipieren, planen und ausführen SpecIF:shows Stationszeichnung
- SP_KV_MSNS_2_Sammelprojekt-MSNS--Netzauftrag konzipieren, planen und ausführen SpecIF:shows Stationsbauauftrag
- SP_KV_MSNS_2_Sammelprojekt-MSNS--Netzauftrag konzipieren, planen und ausführen SpecIF:shows Bauakte
- SP_KV_MSNS_2_Sammelprojekt-MSNS--Netzauftrag konzipieren, planen und ausführen SpecIF:shows Leistungserfassungsblatt [bestätigt]
- SP_KV_MSNS_2_Sammelprojekt-MSNS--Netzauftrag konzipieren, planen und ausführen SpecIF:shows Bauakte [abgeschlossen]
- SP_KV_MSNS_2_Sammelprojekt-MSNS--Netzauftrag konzipieren, planen und ausführen SpecIF:shows Forking Exclusive Gateway: Art der Kundenanfrage?
- SP_KV_MSNS_2_Sammelprojekt-MSNS--Netzauftrag konzipieren, planen und ausführen SpecIF:shows Kundenanfrage eingegangen
- SP_KV_MSNS_2_Sammelprojekt-MSNS--Netzauftrag konzipieren, planen und ausführen SpecIF:shows 1:HA durchführen / Netzauftrag konzipieren
- SP_KV_MSNS_2_Sammelprojekt-MSNS--Netzauftrag konzipieren, planen und ausführen SpecIF:shows Joining Exclusive Gateway
- SP_KV_MSNS_2_Sammelprojekt-MSNS--Netzauftrag konzipieren, planen und ausführen SpecIF:shows 2:Netzauftrag SKB konzipieren
- SP_KV_MSNS_2_Sammelprojekt-MSNS--Netzauftrag konzipieren, planen und ausführen SpecIF:shows Forking Parallel Gateway
- SP_KV_MSNS_2_Sammelprojekt-MSNS--Netzauftrag konzipieren, planen und ausführen SpecIF:shows Forking Exclusive Gateway: Stationsbau erforderlich?
- SP_KV_MSNS_2_Sammelprojekt-MSNS--Netzauftrag konzipieren, planen und ausführen SpecIF:shows 3:Netzauftrag planen
- SP_KV_MSNS_2_Sammelprojekt-MSNS--Netzauftrag konzipieren, planen und ausführen SpecIF:shows 4:Stationsbau planen
- SP_KV_MSNS_2_Sammelprojekt-MSNS--Netzauftrag konzipieren, planen und ausführen SpecIF:shows 5:Stationsbau ausführen
- SP_KV_MSNS_2_Sammelprojekt-MSNS--Netzauftrag konzipieren, planen und ausführen SpecIF:shows Joining Parallel Gateway
- SP_KV_MSNS_2_Sammelprojekt-MSNS--Netzauftrag konzipieren, planen und ausführen SpecIF:shows Joining Exclusive Gateway
- SP_KV_MSNS_2_Sammelprojekt-MSNS--Netzauftrag konzipieren, planen und ausführen SpecIF:shows 6:Netzauftrag ausführen
- SP_KV_MSNS_2_Sammelprojekt-MSNS--Netzauftrag konzipieren, planen und ausführen SpecIF:shows Projekt in Betrieb überführt
- SP_KV_MSNS_2_Sammelprojekt-MSNS--Netzauftrag konzipieren, planen und ausführen SpecIF:shows 7:Netzauftrag in Betrieb überführen
- SP_KV_MSNS_2_Sammelprojekt-MSNS--Netzauftrag konzipieren, planen und ausführen SpecIF:shows Kundenanfrage Niederspannung
- SP_KV_MSNS_2_Sammelprojekt-MSNS--Netzauftrag konzipieren, planen und ausführen SpecIF:shows Mittelspannung 10kV (>2MVA)
- SP_KV_MSNS_2_Sammelprojekt-MSNS--Netzauftrag konzipieren, planen und ausführen SpecIF:shows Ja
- SP_KV_MSNS_2_Sammelprojekt-MSNS--Netzauftrag konzipieren, planen und ausführen SpecIF:shows Nein
- Sammelprojekt -MS/NS--Netzauftrag konzipieren-Netzauftrag für HA-Kunden konzipieren SpecIF:contains Asset Service - Anschlussberater/Sonderanschlussberater
- Sammelprojekt -MS/NS--Netzauftrag konzipieren-Netzauftrag für HA-Kunden konzipieren SpecIF:contains Asset Service - Netzkonzeption
- 9:Kundenanfrage bewerten SpecIF:reads Kundenanfrage [initial]
- 9:Kundenanfrage bewerten SpecIF:writes Kundenanfrage [bewertet Berater]
- Asset Service - Anschlussberater/Sonderanschlussberater SpecIF:contains 9:Kundenanfrage bewerten
- 8:Kundenanfrage aufnehmen SpecIF:reads Kundenanfrage [initial]
- 8:Kundenanfrage aufnehmen SpecIF:writes ECM (Doxis)
- 8:Kundenanfrage aufnehmen SpecIF:writes HAM
- Asset Service - Anschlussberater/Sonderanschlussberater SpecIF:contains 8:Kundenanfrage aufnehmen
- Kundenanfrage NS eingegangen SpecIF:writes Kundenanfrage [initial]
- Asset Service - Anschlussberater/Sonderanschlussberater SpecIF:contains Kundenanfrage NS eingegangen
- 10:Technische Prüfung durchführen SpecIF:reads Kundenanfrage [bewertet Berater]
- 10:Technische Prüfung durchführen SpecIF:reads NIS
- 10:Technische Prüfung durchführen SpecIF:reads LiveLink
- 10:Technische Prüfung durchführen SpecIF:reads Sachdatenportal
- 10:Technische Prüfung durchführen SpecIF:reads ECM (Doxis)
- 10:Technische Prüfung durchführen SpecIF:reads Ledan
- 10:Technische Prüfung durchführen SpecIF:reads MS Excel - Leistungsberechnung
- 10:Technische Prüfung durchführen SpecIF:writes Kundenanfrage [technisch geprüft]
- Asset Service - Netzkonzeption SpecIF:contains 10:Technische Prüfung durchführen
- 11:Netzauftrag anlegen SpecIF:reads Kundenanfrage [technisch geprüft]
- 11:Netzauftrag anlegen SpecIF:reads SAP (NeMo)
- 11:Netzauftrag anlegen SpecIF:reads AVA
- 11:Netzauftrag anlegen SpecIF:reads SNAP
- 11:Netzauftrag anlegen SpecIF:writes SAP (NeMo)
- 11:Netzauftrag anlegen SpecIF:writes NIS
- 11:Netzauftrag anlegen SpecIF:writes AVA
- Asset Service - Netzkonzeption SpecIF:contains 11:Netzauftrag anlegen
- 12:Technisches Konzept erstellen SpecIF:reads NIS
- 12:Technisches Konzept erstellen SpecIF:reads Maßnahmenempfehlungs-Liste
- 12:Technisches Konzept erstellen SpecIF:writes Technisches Konzept [erstellt]
- Asset Service - Netzkonzeption SpecIF:contains 12:Technisches Konzept erstellen
- 46:Kostenschätzung erstellen SpecIF:reads SNAP
- 46:Kostenschätzung erstellen SpecIF:reads AVA
- 46:Kostenschätzung erstellen SpecIF:reads Technisches Konzept [erstellt]
- 46:Kostenschätzung erstellen SpecIF:writes AVA
- Asset Service - Netzkonzeption SpecIF:contains 46:Kostenschätzung erstellen
- 13:Angebot erstellen SpecIF:reads Technisches Konzept [erstellt]
- 13:Angebot erstellen SpecIF:reads HAM
- 13:Angebot erstellen SpecIF:writes HAM
- 13:Angebot erstellen SpecIF:writes Kundenangebot
- Asset Service - Anschlussberater/Sonderanschlussberater SpecIF:contains 13:Angebot erstellen
- Asset Service - Anschlussberater/Sonderanschlussberater SpecIF:contains intermediateCatchEvent
- 15:Netzauftrag schließen SpecIF:reads SAP (NeMo)
- 15:Netzauftrag schließen SpecIF:writes HAM
- 15:Netzauftrag schließen SpecIF:writes SAP (NeMo)
- Asset Service - Netzkonzeption SpecIF:contains 15:Netzauftrag schließen
- Asset Service - Netzkonzeption SpecIF:contains Netzauftrag geschlossen
- 14:Interne Beauftragung der Netzkonzeption SpecIF:reads Beauftragung Kunde
- 14:Interne Beauftragung der Netzkonzeption SpecIF:reads HAM
- 14:Interne Beauftragung der Netzkonzeption SpecIF:writes Baufreigabe
- 14:Interne Beauftragung der Netzkonzeption SpecIF:writes HAM
- Asset Service - Anschlussberater/Sonderanschlussberater SpecIF:contains 14:Interne Beauftragung der Netzkonzeption
- 16:Fachbereiche abfragen/mitnehmen SpecIF:reads Baufreigabe
- 16:Fachbereiche abfragen/mitnehmen SpecIF:reads Technisches Konzept [erstellt]
- 16:Fachbereiche abfragen/mitnehmen SpecIF:reads SAP (NeMo)
- 16:Fachbereiche abfragen/mitnehmen SpecIF:reads AVA
- 16:Fachbereiche abfragen/mitnehmen SpecIF:reads SNAP
- 16:Fachbereiche abfragen/mitnehmen SpecIF:writes Technisches Konzept [HA final konzipiert]
- 16:Fachbereiche abfragen/mitnehmen SpecIF:writes SAP (NeMo)
- 16:Fachbereiche abfragen/mitnehmen SpecIF:writes AVA
- Asset Service - Netzkonzeption SpecIF:contains 16:Fachbereiche abfragen/mitnehmen
- 17:Maßnahmen berücksichtigen und beauftragen SpecIF:reads SAP (NeMo)
- 17:Maßnahmen berücksichtigen und beauftragen SpecIF:writes Technisches Konzept [final konzipiert]
- 17:Maßnahmen berücksichtigen und beauftragen SpecIF:writes SAP (NeMo)
- Asset Service - Netzkonzeption SpecIF:contains 17:Maßnahmen berücksichtigen und beauftragen
- Netzauftrag ist konzipiert SpecIF:reads Technisches Konzept [final konzipiert]
- Asset Service - Netzkonzeption SpecIF:contains Netzauftrag ist konzipiert
- 8:Kundenanfrage aufnehmen SpecIF:precedes 9:Kundenanfrage bewerten
- Kundenanfrage NS eingegangen SpecIF:triggers 8:Kundenanfrage aufnehmen
- 9:Kundenanfrage bewerten SpecIF:precedes Forking Exclusive Gateway: Netzmaßnahme notwendig?
- Forking Exclusive Gateway: Netzmaßnahme notwendig? SpecIF:signals Ja
- Ja SpecIF:triggers 10:Technische Prüfung durchführen
- Forking Exclusive Gateway: Netzmaßnahme notwendig? SpecIF:signals Nein
- Nein SpecIF:triggers Joining Exclusive Gateway
- 10:Technische Prüfung durchführen SpecIF:precedes Forking Exclusive Gateway: Netzauftrag erforderlich?
- Forking Exclusive Gateway: Netzauftrag erforderlich? SpecIF:signals Nein
- Nein SpecIF:triggers Joining Exclusive Gateway
- Joining Exclusive Gateway SpecIF:precedes Joining Exclusive Gateway
- Forking Exclusive Gateway: Netzauftrag erforderlich? SpecIF:signals Ja
- Ja SpecIF:triggers 11:Netzauftrag anlegen
- 11:Netzauftrag anlegen SpecIF:precedes 12:Technisches Konzept erstellen
- 12:Technisches Konzept erstellen SpecIF:precedes 46:Kostenschätzung erstellen
- Joining Exclusive Gateway SpecIF:precedes 13:Angebot erstellen
- 13:Angebot erstellen SpecIF:precedes Forking Exclusive Gateway: Angebot vom Kunden angenommen?
- Forking Exclusive Gateway: Angebot vom Kunden angenommen? SpecIF:signals Ja
- Ja SpecIF:triggers 14:Interne Beauftragung der Netzkonzeption
- Forking Exclusive Gateway: Angebot vom Kunden angenommen? SpecIF:signals Nein
- Nein SpecIF:triggers intermediateCatchEvent
- intermediateCatchEvent SpecIF:triggers 15:Netzauftrag schließen
- 14:Interne Beauftragung der Netzkonzeption SpecIF:precedes 16:Fachbereiche abfragen/mitnehmen
- 15:Netzauftrag schließen SpecIF:signals Netzauftrag geschlossen
- 16:Fachbereiche abfragen/mitnehmen SpecIF:precedes 17:Maßnahmen berücksichtigen und beauftragen
- 17:Maßnahmen berücksichtigen und beauftragen SpecIF:signals Netzauftrag ist konzipiert
- 46:Kostenschätzung erstellen SpecIF:precedes Joining Exclusive Gateway
- Text Annotation 01 SpecIF:refersTo SAP (NeMo)
- Text Annotation 04 SpecIF:refersTo NIS
- Text Annotation 05 SpecIF:refersTo 12:Technisches Konzept erstellen
- Text Annotation 02 SpecIF:refersTo Technisches Konzept [erstellt]
- Text Annotation 03 SpecIF:refersTo Technisches Konzept [HA final konzipiert]
- Text Annotation 05 SpecIF:refersTo 16:Fachbereiche abfragen/mitnehmen
- Text Annotation 06 SpecIF:refersTo Kundenanfrage [initial]
- Text Annotation 08 SpecIF:refersTo ECM (Doxis)
- Text Annotation 07 SpecIF:refersTo Kundenanfrage [bewertet Berater]
- Text Annotation 09 SpecIF:refersTo Forking Exclusive Gateway: Netzauftrag erforderlich?
- Text Annotation 11 SpecIF:refersTo 11:Netzauftrag anlegen
- Text Annotation 10 SpecIF:refersTo Maßnahmenempfehlungs-Liste
- Text Annotation 12 SpecIF:refersTo 12:Technisches Konzept erstellen
- Text Annotation 16 SpecIF:refersTo 13:Angebot erstellen
- Text Annotation 15 SpecIF:refersTo intermediateCatchEvent
- Text Annotation 13 SpecIF:refersTo HAM
- Text Annotation 14 SpecIF:refersTo 16:Fachbereiche abfragen/mitnehmen
- Text Annotation 17 SpecIF:refersTo 46:Kostenschätzung erstellen
- Text Annotation 18 SpecIF:refersTo 46:Kostenschätzung erstellen
- Text Annotation 19 SpecIF:refersTo SNAP
- Text Annotation 20 SpecIF:refersTo Kundenangebot
- Text Annotation 21 SpecIF:refersTo 16:Fachbereiche abfragen/mitnehmen
- Text Annotation 22 SpecIF:refersTo SNAP
- Text Annotation 23 SpecIF:refersTo SNAP
- SP_KV_MSNS_2A_Sammelprojekt-MSNS--Netzauftrag konzipieren_HA SpecIF:shows Sammelprojekt -MS/NS--Netzauftrag konzipieren-Netzauftrag für HA-Kunden konzipieren
- SP_KV_MSNS_2A_Sammelprojekt-MSNS--Netzauftrag konzipieren_HA SpecIF:shows Asset Service - Anschlussberater/Sonderanschlussberater
- SP_KV_MSNS_2A_Sammelprojekt-MSNS--Netzauftrag konzipieren_HA SpecIF:shows Asset Service - Netzkonzeption
- SP_KV_MSNS_2A_Sammelprojekt-MSNS--Netzauftrag konzipieren_HA SpecIF:shows Kundenanfrage [initial]
- SP_KV_MSNS_2A_Sammelprojekt-MSNS--Netzauftrag konzipieren_HA SpecIF:shows ECM (Doxis)
- SP_KV_MSNS_2A_Sammelprojekt-MSNS--Netzauftrag konzipieren_HA SpecIF:shows HAM
- SP_KV_MSNS_2A_Sammelprojekt-MSNS--Netzauftrag konzipieren_HA SpecIF:shows Kundenanfrage [technisch geprüft]
- SP_KV_MSNS_2A_Sammelprojekt-MSNS--Netzauftrag konzipieren_HA SpecIF:shows Kundenanfrage [bewertet Berater]
- SP_KV_MSNS_2A_Sammelprojekt-MSNS--Netzauftrag konzipieren_HA SpecIF:shows MS Excel - Leistungsberechnung
- SP_KV_MSNS_2A_Sammelprojekt-MSNS--Netzauftrag konzipieren_HA SpecIF:shows NIS
- SP_KV_MSNS_2A_Sammelprojekt-MSNS--Netzauftrag konzipieren_HA SpecIF:shows LiveLink
- SP_KV_MSNS_2A_Sammelprojekt-MSNS--Netzauftrag konzipieren_HA SpecIF:shows Sachdatenportal
- SP_KV_MSNS_2A_Sammelprojekt-MSNS--Netzauftrag konzipieren_HA SpecIF:shows Ledan
- SP_KV_MSNS_2A_Sammelprojekt-MSNS--Netzauftrag konzipieren_HA SpecIF:shows AVA
- SP_KV_MSNS_2A_Sammelprojekt-MSNS--Netzauftrag konzipieren_HA SpecIF:shows SNAP
- SP_KV_MSNS_2A_Sammelprojekt-MSNS--Netzauftrag konzipieren_HA SpecIF:shows SAP (NeMo)
- SP_KV_MSNS_2A_Sammelprojekt-MSNS--Netzauftrag konzipieren_HA SpecIF:shows Technisches Konzept [erstellt]
- SP_KV_MSNS_2A_Sammelprojekt-MSNS--Netzauftrag konzipieren_HA SpecIF:shows Maßnahmenempfehlungs-Liste
- SP_KV_MSNS_2A_Sammelprojekt-MSNS--Netzauftrag konzipieren_HA SpecIF:shows Kundenangebot
- SP_KV_MSNS_2A_Sammelprojekt-MSNS--Netzauftrag konzipieren_HA SpecIF:shows Beauftragung Kunde
- SP_KV_MSNS_2A_Sammelprojekt-MSNS--Netzauftrag konzipieren_HA SpecIF:shows Baufreigabe
- SP_KV_MSNS_2A_Sammelprojekt-MSNS--Netzauftrag konzipieren_HA SpecIF:shows Technisches Konzept [final konzipiert]
- SP_KV_MSNS_2A_Sammelprojekt-MSNS--Netzauftrag konzipieren_HA SpecIF:shows Technisches Konzept [HA final konzipiert]
- SP_KV_MSNS_2A_Sammelprojekt-MSNS--Netzauftrag konzipieren_HA SpecIF:shows 9:Kundenanfrage bewerten
- SP_KV_MSNS_2A_Sammelprojekt-MSNS--Netzauftrag konzipieren_HA SpecIF:shows 8:Kundenanfrage aufnehmen
- SP_KV_MSNS_2A_Sammelprojekt-MSNS--Netzauftrag konzipieren_HA SpecIF:shows Forking Exclusive Gateway: Netzmaßnahme notwendig?
- SP_KV_MSNS_2A_Sammelprojekt-MSNS--Netzauftrag konzipieren_HA SpecIF:shows Kundenanfrage NS eingegangen
- SP_KV_MSNS_2A_Sammelprojekt-MSNS--Netzauftrag konzipieren_HA SpecIF:shows 10:Technische Prüfung durchführen
- SP_KV_MSNS_2A_Sammelprojekt-MSNS--Netzauftrag konzipieren_HA SpecIF:shows Joining Exclusive Gateway
- SP_KV_MSNS_2A_Sammelprojekt-MSNS--Netzauftrag konzipieren_HA SpecIF:shows Forking Exclusive Gateway: Netzauftrag erforderlich?
- SP_KV_MSNS_2A_Sammelprojekt-MSNS--Netzauftrag konzipieren_HA SpecIF:shows 11:Netzauftrag anlegen
- SP_KV_MSNS_2A_Sammelprojekt-MSNS--Netzauftrag konzipieren_HA SpecIF:shows 12:Technisches Konzept erstellen
- SP_KV_MSNS_2A_Sammelprojekt-MSNS--Netzauftrag konzipieren_HA SpecIF:shows 46:Kostenschätzung erstellen
- SP_KV_MSNS_2A_Sammelprojekt-MSNS--Netzauftrag konzipieren_HA SpecIF:shows 13:Angebot erstellen
- SP_KV_MSNS_2A_Sammelprojekt-MSNS--Netzauftrag konzipieren_HA SpecIF:shows Joining Exclusive Gateway
- SP_KV_MSNS_2A_Sammelprojekt-MSNS--Netzauftrag konzipieren_HA SpecIF:shows Forking Exclusive Gateway: Angebot vom Kunden angenommen?
- SP_KV_MSNS_2A_Sammelprojekt-MSNS--Netzauftrag konzipieren_HA SpecIF:shows intermediateCatchEvent
- SP_KV_MSNS_2A_Sammelprojekt-MSNS--Netzauftrag konzipieren_HA SpecIF:shows 15:Netzauftrag schließen
- SP_KV_MSNS_2A_Sammelprojekt-MSNS--Netzauftrag konzipieren_HA SpecIF:shows Netzauftrag geschlossen
- SP_KV_MSNS_2A_Sammelprojekt-MSNS--Netzauftrag konzipieren_HA SpecIF:shows 14:Interne Beauftragung der Netzkonzeption
- SP_KV_MSNS_2A_Sammelprojekt-MSNS--Netzauftrag konzipieren_HA SpecIF:shows 16:Fachbereiche abfragen/mitnehmen
- SP_KV_MSNS_2A_Sammelprojekt-MSNS--Netzauftrag konzipieren_HA SpecIF:shows 17:Maßnahmen berücksichtigen und beauftragen
- SP_KV_MSNS_2A_Sammelprojekt-MSNS--Netzauftrag konzipieren_HA SpecIF:shows Netzauftrag ist konzipiert
- SP_KV_MSNS_2A_Sammelprojekt-MSNS--Netzauftrag konzipieren_HA SpecIF:shows Ja
- SP_KV_MSNS_2A_Sammelprojekt-MSNS--Netzauftrag konzipieren_HA SpecIF:shows Nein
- SP_KV_MSNS_2A_Sammelprojekt-MSNS--Netzauftrag konzipieren_HA SpecIF:shows Nein
- SP_KV_MSNS_2A_Sammelprojekt-MSNS--Netzauftrag konzipieren_HA SpecIF:shows Ja
- SP_KV_MSNS_2A_Sammelprojekt-MSNS--Netzauftrag konzipieren_HA SpecIF:shows Ja
- SP_KV_MSNS_2A_Sammelprojekt-MSNS--Netzauftrag konzipieren_HA SpecIF:shows Nein
- Sammelprojekt -MS/NS--Netzauftrag konzipieren-Netzauftrag für Sonderkunden konzipieren SpecIF:contains Asset Service - Sonderkundenberater (SKB)
- Sammelprojekt -MS/NS--Netzauftrag konzipieren-Netzauftrag für Sonderkunden konzipieren SpecIF:contains Asset Service - Netzkonzeption
- 18:Kundenanfrage aufnehmen SpecIF:reads Kundenanfrage [initial]
- 18:Kundenanfrage aufnehmen SpecIF:writes NKT XRM
- Asset Service - Sonderkundenberater (SKB) SpecIF:contains 18:Kundenanfrage aufnehmen
- Kundenanfrage MS 10kV (>2MVA) eingegangen SpecIF:writes Kundenanfrage [initial]
- Asset Service - Sonderkundenberater (SKB) SpecIF:contains Kundenanfrage MS 10kV (>2MVA) eingegangen
- 20:Netzauftrag anlegen SpecIF:reads Kundenanfrage [bewertet Konzeption]
- 20:Netzauftrag anlegen SpecIF:reads AVA
- 20:Netzauftrag anlegen SpecIF:reads SNAP
- 20:Netzauftrag anlegen SpecIF:writes SAP (NeMo)
- 20:Netzauftrag anlegen SpecIF:writes AVA
- Asset Service - Netzkonzeption SpecIF:contains 20:Netzauftrag anlegen
- 21:Technisches Konzept erstellen SpecIF:reads NIS
- 21:Technisches Konzept erstellen SpecIF:reads Maßnahmenempfehlungs-Liste
- 21:Technisches Konzept erstellen SpecIF:writes Technisches Konzept [erstellt]
- Asset Service - Netzkonzeption SpecIF:contains 21:Technisches Konzept erstellen
- 19:Kundenanfrage bewerten SpecIF:reads Kundenanfrage [initial]
- 19:Kundenanfrage bewerten SpecIF:writes Kundenanfrage [bewertet Konzeption]
- Asset Service - Netzkonzeption SpecIF:contains 19:Kundenanfrage bewerten
- 23:Angebot erstellen SpecIF:reads Technisches Konzept [kalkuliert]
- 23:Angebot erstellen SpecIF:reads NKT XRM
- 23:Angebot erstellen SpecIF:writes NKT XRM
- 23:Angebot erstellen SpecIF:writes Kundenangebot
- 23:Angebot erstellen SpecIF:writes Baufreigabe
- Asset Service - Sonderkundenberater (SKB) SpecIF:contains 23:Angebot erstellen
- 22:Kalkulation erstellen SpecIF:reads Angebotsblatt
- 22:Kalkulation erstellen SpecIF:reads Technisches Konzept [erstellt]
- 22:Kalkulation erstellen SpecIF:reads SNAP
- 22:Kalkulation erstellen SpecIF:reads AVA
- 22:Kalkulation erstellen SpecIF:writes Technisches Konzept [kalkuliert]
- 22:Kalkulation erstellen SpecIF:writes AVA
- Asset Service - Netzkonzeption SpecIF:contains 22:Kalkulation erstellen
- 24:Netzauftrag schließen SpecIF:reads SAP (NeMo)
- 24:Netzauftrag schließen SpecIF:writes NKT XRM
- 24:Netzauftrag schließen SpecIF:writes SAP (NeMo)
- Asset Service - Netzkonzeption SpecIF:contains 24:Netzauftrag schließen
- Asset Service - Sonderkundenberater (SKB) SpecIF:contains intermediateCatchEvent
- 25:Fachbereiche abfragen/mitnehmen SpecIF:reads Baufreigabe
- 25:Fachbereiche abfragen/mitnehmen SpecIF:reads Technisches Konzept [kalkuliert]
- 25:Fachbereiche abfragen/mitnehmen SpecIF:reads NKT XRM
- 25:Fachbereiche abfragen/mitnehmen SpecIF:reads SNAP
- 25:Fachbereiche abfragen/mitnehmen SpecIF:reads AVA
- 25:Fachbereiche abfragen/mitnehmen SpecIF:writes Technisches Konzept [SKB final konzipiert]
- 25:Fachbereiche abfragen/mitnehmen SpecIF:writes NKT XRM
- 25:Fachbereiche abfragen/mitnehmen SpecIF:writes AVA
- Asset Service - Netzkonzeption SpecIF:contains 25:Fachbereiche abfragen/mitnehmen
- 26:Maßnahmen berücksichtigen und beauftragen SpecIF:reads NKT XRM
- 26:Maßnahmen berücksichtigen und beauftragen SpecIF:writes Technisches Konzept [final konzipiert]
- 26:Maßnahmen berücksichtigen und beauftragen SpecIF:writes NKT XRM
- Asset Service - Netzkonzeption SpecIF:contains 26:Maßnahmen berücksichtigen und beauftragen
- 18:Kundenanfrage aufnehmen SpecIF:precedes 19:Kundenanfrage bewerten
- Kundenanfrage MS 10kV (>2MVA) eingegangen SpecIF:triggers 18:Kundenanfrage aufnehmen
- 19:Kundenanfrage bewerten SpecIF:precedes 20:Netzauftrag anlegen
- 20:Netzauftrag anlegen SpecIF:precedes 21:Technisches Konzept erstellen
- 21:Technisches Konzept erstellen SpecIF:precedes 22:Kalkulation erstellen
- 23:Angebot erstellen SpecIF:precedes Forking Exclusive Gateway: Angebot vom Kunden angenommen?
- Forking Exclusive Gateway: Angebot vom Kunden angenommen? SpecIF:signals Nein
- Nein SpecIF:triggers intermediateCatchEvent
- Forking Exclusive Gateway: Angebot vom Kunden angenommen? SpecIF:signals Ja
- Ja SpecIF:triggers 25:Fachbereiche abfragen/mitnehmen
- 22:Kalkulation erstellen SpecIF:precedes 23:Angebot erstellen
- 24:Netzauftrag schließen SpecIF:signals Netzauftrag geschlossen
- intermediateCatchEvent SpecIF:triggers 24:Netzauftrag schließen
- 26:Maßnahmen berücksichtigen und beauftragen SpecIF:signals Netzauftrag ist konzipiert
- 25:Fachbereiche abfragen/mitnehmen SpecIF:precedes 26:Maßnahmen berücksichtigen und beauftragen
- Text Annotation 01 SpecIF:refersTo Kundenanfrage [bewertet Konzeption]
- Text Annotation 03 SpecIF:refersTo Technisches Konzept [erstellt]
- Text Annotation 04 SpecIF:refersTo Technisches Konzept [kalkuliert]
- Text Annotation 05 SpecIF:refersTo Technisches Konzept [SKB final konzipiert]
- Text Annotation 06 SpecIF:refersTo Kundenanfrage [initial]
- Text Annotation 02 SpecIF:refersTo SAP (NeMo)
- Text Annotation 07 SpecIF:refersTo 20:Netzauftrag anlegen
- Text Annotation 11 SpecIF:refersTo 22:Kalkulation erstellen
- Text Annotation 09 SpecIF:refersTo Kundenangebot
- Text Annotation 10 SpecIF:refersTo intermediateCatchEvent
- Text Annotation 08 SpecIF:refersTo SNAP
- Text Annotation 12 SpecIF:refersTo 21:Technisches Konzept erstellen
- Text Annotation 13 SpecIF:refersTo 25:Fachbereiche abfragen/mitnehmen
- Text Annotation 14 SpecIF:refersTo SNAP
- Text Annotation 15 SpecIF:refersTo SNAP
- SP_KV_MSNS_2B_Sammelprojekt-MSNS--Netzauftrag konzipieren-SKB SpecIF:shows Sammelprojekt -MS/NS--Netzauftrag konzipieren-Netzauftrag für Sonderkunden konzipieren
- SP_KV_MSNS_2B_Sammelprojekt-MSNS--Netzauftrag konzipieren-SKB SpecIF:shows Asset Service - Sonderkundenberater (SKB)
- SP_KV_MSNS_2B_Sammelprojekt-MSNS--Netzauftrag konzipieren-SKB SpecIF:shows Asset Service - Netzkonzeption
- SP_KV_MSNS_2B_Sammelprojekt-MSNS--Netzauftrag konzipieren-SKB SpecIF:shows NKT XRM
- SP_KV_MSNS_2B_Sammelprojekt-MSNS--Netzauftrag konzipieren-SKB SpecIF:shows Kundenanfrage [initial]
- SP_KV_MSNS_2B_Sammelprojekt-MSNS--Netzauftrag konzipieren-SKB SpecIF:shows Kundenanfrage [bewertet Konzeption]
- SP_KV_MSNS_2B_Sammelprojekt-MSNS--Netzauftrag konzipieren-SKB SpecIF:shows Technisches Konzept [erstellt]
- SP_KV_MSNS_2B_Sammelprojekt-MSNS--Netzauftrag konzipieren-SKB SpecIF:shows NIS
- SP_KV_MSNS_2B_Sammelprojekt-MSNS--Netzauftrag konzipieren-SKB SpecIF:shows Maßnahmenempfehlungs-Liste
- SP_KV_MSNS_2B_Sammelprojekt-MSNS--Netzauftrag konzipieren-SKB SpecIF:shows SAP (NeMo)
- SP_KV_MSNS_2B_Sammelprojekt-MSNS--Netzauftrag konzipieren-SKB SpecIF:shows AVA
- SP_KV_MSNS_2B_Sammelprojekt-MSNS--Netzauftrag konzipieren-SKB SpecIF:shows SNAP
- SP_KV_MSNS_2B_Sammelprojekt-MSNS--Netzauftrag konzipieren-SKB SpecIF:shows Angebotsblatt
- SP_KV_MSNS_2B_Sammelprojekt-MSNS--Netzauftrag konzipieren-SKB SpecIF:shows Technisches Konzept [kalkuliert]
- SP_KV_MSNS_2B_Sammelprojekt-MSNS--Netzauftrag konzipieren-SKB SpecIF:shows Baufreigabe
- SP_KV_MSNS_2B_Sammelprojekt-MSNS--Netzauftrag konzipieren-SKB SpecIF:shows Kundenangebot
- SP_KV_MSNS_2B_Sammelprojekt-MSNS--Netzauftrag konzipieren-SKB SpecIF:shows Technisches Konzept [SKB final konzipiert]
- SP_KV_MSNS_2B_Sammelprojekt-MSNS--Netzauftrag konzipieren-SKB SpecIF:shows Technisches Konzept [final konzipiert]
- SP_KV_MSNS_2B_Sammelprojekt-MSNS--Netzauftrag konzipieren-SKB SpecIF:shows 18:Kundenanfrage aufnehmen
- SP_KV_MSNS_2B_Sammelprojekt-MSNS--Netzauftrag konzipieren-SKB SpecIF:shows Kundenanfrage MS 10kV (>2MVA) eingegangen
- SP_KV_MSNS_2B_Sammelprojekt-MSNS--Netzauftrag konzipieren-SKB SpecIF:shows 20:Netzauftrag anlegen
- SP_KV_MSNS_2B_Sammelprojekt-MSNS--Netzauftrag konzipieren-SKB SpecIF:shows 21:Technisches Konzept erstellen
- SP_KV_MSNS_2B_Sammelprojekt-MSNS--Netzauftrag konzipieren-SKB SpecIF:shows 19:Kundenanfrage bewerten
- SP_KV_MSNS_2B_Sammelprojekt-MSNS--Netzauftrag konzipieren-SKB SpecIF:shows Forking Exclusive Gateway: Angebot vom Kunden angenommen?
- SP_KV_MSNS_2B_Sammelprojekt-MSNS--Netzauftrag konzipieren-SKB SpecIF:shows 23:Angebot erstellen
- SP_KV_MSNS_2B_Sammelprojekt-MSNS--Netzauftrag konzipieren-SKB SpecIF:shows 22:Kalkulation erstellen
- SP_KV_MSNS_2B_Sammelprojekt-MSNS--Netzauftrag konzipieren-SKB SpecIF:shows Netzauftrag geschlossen
- SP_KV_MSNS_2B_Sammelprojekt-MSNS--Netzauftrag konzipieren-SKB SpecIF:shows 24:Netzauftrag schließen
- SP_KV_MSNS_2B_Sammelprojekt-MSNS--Netzauftrag konzipieren-SKB SpecIF:shows intermediateCatchEvent
- SP_KV_MSNS_2B_Sammelprojekt-MSNS--Netzauftrag konzipieren-SKB SpecIF:shows 25:Fachbereiche abfragen/mitnehmen
- SP_KV_MSNS_2B_Sammelprojekt-MSNS--Netzauftrag konzipieren-SKB SpecIF:shows Netzauftrag ist konzipiert
- SP_KV_MSNS_2B_Sammelprojekt-MSNS--Netzauftrag konzipieren-SKB SpecIF:shows 26:Maßnahmen berücksichtigen und beauftragen
- SP_KV_MSNS_2B_Sammelprojekt-MSNS--Netzauftrag konzipieren-SKB SpecIF:shows Nein
- SP_KV_MSNS_2B_Sammelprojekt-MSNS--Netzauftrag konzipieren-SKB SpecIF:shows Ja
- Sammelprojekt-MS/NS--Netzauftrag planen SpecIF:contains Asset Service - Netzplaner
- Sammelprojekt-MS/NS--Netzauftrag planen SpecIF:contains Asset Service - Netzkonzeption
- Sammelprojekt-MS/NS--Netzauftrag planen SpecIF:contains Asset Management
- 28:Technisches Konzept nacharbeiten SpecIF:reads Technisches Konzept [bemängelt]
- 28:Technisches Konzept nacharbeiten SpecIF:writes Technisches Konzept [final konzipiert]
- Asset Service - Netzkonzeption SpecIF:contains 28:Technisches Konzept nacharbeiten
- Netzauftrag ist konzipiert SpecIF:writes Technisches Konzept [final konzipiert]
- Asset Service - Netzplaner SpecIF:contains Netzauftrag ist konzipiert
- 27:Vollständigkeit der Unterlagen und Machbarkeit prüfen SpecIF:reads Technisches Konzept [final konzipiert]
- 27:Vollständigkeit der Unterlagen und Machbarkeit prüfen SpecIF:writes Technisches Konzept [geprüft]
- 27:Vollständigkeit der Unterlagen und Machbarkeit prüfen SpecIF:writes Technisches Konzept [bemängelt]
- Asset Service - Netzplaner SpecIF:contains 27:Vollständigkeit der Unterlagen und Machbarkeit prüfen
- 29:Genehmigungsplan erstellen SpecIF:reads Technisches Konzept [geprüft]
- 29:Genehmigungsplan erstellen SpecIF:reads NIS
- 29:Genehmigungsplan erstellen SpecIF:reads LiveLink
- 29:Genehmigungsplan erstellen SpecIF:reads Sachdatenportal
- 29:Genehmigungsplan erstellen SpecIF:reads ECM (Doxis)
- 29:Genehmigungsplan erstellen SpecIF:reads Alkis
- 29:Genehmigungsplan erstellen SpecIF:writes Genehmigungsplan
- 29:Genehmigungsplan erstellen SpecIF:writes infreSt
- Asset Service - Netzplaner SpecIF:contains 29:Genehmigungsplan erstellen
- Genehmigungen/Leitungsauskünfte erhalten SpecIF:writes Genehmigungen/Leitungsauskünfte
- Asset Service - Netzplaner SpecIF:contains Genehmigungen/Leitungsauskünfte erhalten
- Netzauftrag ist beauftragt SpecIF:reads Bauakte
- Asset Service - Netzplaner SpecIF:contains Netzauftrag ist beauftragt
- 35:Bauakte zusammenstellen und beauftragen SpecIF:reads Ausführungsplan [erweitert]
- 35:Bauakte zusammenstellen und beauftragen SpecIF:reads Technisches Konzept [final konzipiert]
- 35:Bauakte zusammenstellen und beauftragen SpecIF:reads Genehmigungen/Leitungsauskünfte
- 35:Bauakte zusammenstellen und beauftragen SpecIF:writes Bauakte
- 35:Bauakte zusammenstellen und beauftragen SpecIF:writes Netzbauauftrag
- 35:Bauakte zusammenstellen und beauftragen SpecIF:writes Vertrag/Verträge mit AN
- 35:Bauakte zusammenstellen und beauftragen SpecIF:writes AVA
- Asset Service - Netzplaner SpecIF:contains 35:Bauakte zusammenstellen und beauftragen
- 33:Über zusätzliches Budget entscheiden SpecIF:reads Budgetforderung
- 33:Über zusätzliches Budget entscheiden SpecIF:reads Ausführungsplan [erweitert]
- 33:Über zusätzliches Budget entscheiden SpecIF:writes Budgetentscheidung
- Asset Management SpecIF:contains 33:Über zusätzliches Budget entscheiden
- 32:Budget nachfordern SpecIF:reads Ausführungsplan [erweitert]
- 32:Budget nachfordern SpecIF:writes Budgetforderung
- Asset Service - Netzplaner SpecIF:contains 32:Budget nachfordern
- Asset Management SpecIF:contains Planung beendet
- 34:Ausschreibung begleiten oder Abruf aus Rahmenvertrag SpecIF:reads AVA
- 34:Ausschreibung begleiten oder Abruf aus Rahmenvertrag SpecIF:reads Ausführungsplan [erweitert]
- 34:Ausschreibung begleiten oder Abruf aus Rahmenvertrag SpecIF:writes Ausschreibungsunterlagen
- 34:Ausschreibung begleiten oder Abruf aus Rahmenvertrag SpecIF:writes SAP
- Asset Service - Netzplaner SpecIF:contains 34:Ausschreibung begleiten oder Abruf aus Rahmenvertrag
- 31:MuF kalkulieren und Budget prüfen SpecIF:reads Ausführungsplan [initial]
- 31:MuF kalkulieren und Budget prüfen SpecIF:reads AVA
- 31:MuF kalkulieren und Budget prüfen SpecIF:reads SAP (NeMo)
- 31:MuF kalkulieren und Budget prüfen SpecIF:writes AVA
- 31:MuF kalkulieren und Budget prüfen SpecIF:writes Ausführungsplan [erweitert]
- Asset Service - Netzplaner SpecIF:contains 31:MuF kalkulieren und Budget prüfen
- 30:Ausführungsplan erstellen SpecIF:reads Genehmigungen/Leitungsauskünfte
- 30:Ausführungsplan erstellen SpecIF:reads Genehmigungsplan
- 30:Ausführungsplan erstellen SpecIF:reads NIS
- 30:Ausführungsplan erstellen SpecIF:reads LiveLink
- 30:Ausführungsplan erstellen SpecIF:reads Sachdatenportal
- 30:Ausführungsplan erstellen SpecIF:reads ECM (Doxis)
- 30:Ausführungsplan erstellen SpecIF:writes Ausführungsplan [initial]
- Asset Service - Netzplaner SpecIF:contains 30:Ausführungsplan erstellen
- Forking Exclusive Gateway: Prüfung bestanden? SpecIF:signals Weiter an Genehmigungsplanung
- Weiter an Genehmigungsplanung SpecIF:triggers 29:Genehmigungsplan erstellen
- 27:Vollständigkeit der Unterlagen und Machbarkeit prüfen SpecIF:precedes Forking Exclusive Gateway: Prüfung bestanden?
- Joining Exclusive Gateway SpecIF:precedes 27:Vollständigkeit der Unterlagen und Machbarkeit prüfen
- Netzauftrag ist konzipiert SpecIF:triggers Joining Exclusive Gateway
- Forking Exclusive Gateway: Prüfung bestanden? SpecIF:signals Zurück an Konzeption
- Zurück an Konzeption SpecIF:triggers 28:Technisches Konzept nacharbeiten
- 28:Technisches Konzept nacharbeiten SpecIF:precedes Joining Exclusive Gateway
- 29:Genehmigungsplan erstellen SpecIF:signals Genehmigungen/Leitungsauskünfte erhalten
- Genehmigungen/Leitungsauskünfte erhalten SpecIF:triggers 30:Ausführungsplan erstellen
- 30:Ausführungsplan erstellen SpecIF:precedes 31:MuF kalkulieren und Budget prüfen
- 31:MuF kalkulieren und Budget prüfen SpecIF:precedes Forking Exclusive Gateway: Budget ausreichend?
- Forking Exclusive Gateway: Budget ausreichend? SpecIF:signals Ja
- Ja SpecIF:triggers Joining Exclusive Gateway
- Forking Exclusive Gateway: Zusätzliches Budget genehmigt? SpecIF:signals Ja
- Ja SpecIF:triggers Joining Exclusive Gateway
- Joining Exclusive Gateway SpecIF:precedes 34:Ausschreibung begleiten oder Abruf aus Rahmenvertrag
- 34:Ausschreibung begleiten oder Abruf aus Rahmenvertrag SpecIF:precedes 35:Bauakte zusammenstellen und beauftragen
- 33:Über zusätzliches Budget entscheiden SpecIF:precedes Forking Exclusive Gateway: Zusätzliches Budget genehmigt?
- Forking Exclusive Gateway: Zusätzliches Budget genehmigt? SpecIF:signals Nein
- Nein SpecIF:triggers Planung beendet
- Forking Exclusive Gateway: Budget ausreichend? SpecIF:signals Nein
- Nein SpecIF:triggers 32:Budget nachfordern
- 32:Budget nachfordern SpecIF:precedes 33:Über zusätzliches Budget entscheiden
- 35:Bauakte zusammenstellen und beauftragen SpecIF:signals Netzauftrag ist beauftragt
- Text Annotation 01 SpecIF:refersTo infreSt
- Text Annotation 04 SpecIF:refersTo Netzbauauftrag
- Text Annotation 03 SpecIF:refersTo Bauakte
- Text Annotation 08 SpecIF:refersTo Ausschreibungsunterlagen
- Text Annotation 05 SpecIF:refersTo Ausführungsplan [erweitert]
- Text Annotation 07 SpecIF:refersTo Ausführungsplan [erweitert]
- Text Annotation 02 SpecIF:refersTo 34:Ausschreibung begleiten oder Abruf aus Rahmenvertrag
- Text Annotation 06 SpecIF:refersTo Ausführungsplan [initial]
- Text Annotation 09 SpecIF:refersTo 31:MuF kalkulieren und Budget prüfen
- Text Annotation 10 SpecIF:refersTo AVA
- Text Annotation 10 SpecIF:refersTo SAP
- Text Annotation 11 SpecIF:refersTo 31:MuF kalkulieren und Budget prüfen
- Text Annotation 11 SpecIF:refersTo 30:Ausführungsplan erstellen
- Text Annotation 12 SpecIF:refersTo 34:Ausschreibung begleiten oder Abruf aus Rahmenvertrag
- Text Annotation 11 SpecIF:refersTo 34:Ausschreibung begleiten oder Abruf aus Rahmenvertrag
- SP_KV_MSNS_3_Sammelprojekt-MSNS--Netzauftrag planen SpecIF:shows Sammelprojekt-MS/NS--Netzauftrag planen
- SP_KV_MSNS_3_Sammelprojekt-MSNS--Netzauftrag planen SpecIF:shows Asset Service - Netzplaner
- SP_KV_MSNS_3_Sammelprojekt-MSNS--Netzauftrag planen SpecIF:shows Asset Service - Netzkonzeption
- SP_KV_MSNS_3_Sammelprojekt-MSNS--Netzauftrag planen SpecIF:shows Asset Management
- SP_KV_MSNS_3_Sammelprojekt-MSNS--Netzauftrag planen SpecIF:shows Technisches Konzept [bemängelt]
- SP_KV_MSNS_3_Sammelprojekt-MSNS--Netzauftrag planen SpecIF:shows Technisches Konzept [final konzipiert]
- SP_KV_MSNS_3_Sammelprojekt-MSNS--Netzauftrag planen SpecIF:shows NIS
- SP_KV_MSNS_3_Sammelprojekt-MSNS--Netzauftrag planen SpecIF:shows Sachdatenportal
- SP_KV_MSNS_3_Sammelprojekt-MSNS--Netzauftrag planen SpecIF:shows ECM (Doxis)
- SP_KV_MSNS_3_Sammelprojekt-MSNS--Netzauftrag planen SpecIF:shows Technisches Konzept [geprüft]
- SP_KV_MSNS_3_Sammelprojekt-MSNS--Netzauftrag planen SpecIF:shows LiveLink
- SP_KV_MSNS_3_Sammelprojekt-MSNS--Netzauftrag planen SpecIF:shows Alkis
- SP_KV_MSNS_3_Sammelprojekt-MSNS--Netzauftrag planen SpecIF:shows Genehmigungen/Leitungsauskünfte
- SP_KV_MSNS_3_Sammelprojekt-MSNS--Netzauftrag planen SpecIF:shows Genehmigungsplan
- SP_KV_MSNS_3_Sammelprojekt-MSNS--Netzauftrag planen SpecIF:shows infreSt
- SP_KV_MSNS_3_Sammelprojekt-MSNS--Netzauftrag planen SpecIF:shows Ausführungsplan [erweitert]
- SP_KV_MSNS_3_Sammelprojekt-MSNS--Netzauftrag planen SpecIF:shows Bauakte
- SP_KV_MSNS_3_Sammelprojekt-MSNS--Netzauftrag planen SpecIF:shows AVA
- SP_KV_MSNS_3_Sammelprojekt-MSNS--Netzauftrag planen SpecIF:shows Vertrag/Verträge mit AN
- SP_KV_MSNS_3_Sammelprojekt-MSNS--Netzauftrag planen SpecIF:shows Netzbauauftrag
- SP_KV_MSNS_3_Sammelprojekt-MSNS--Netzauftrag planen SpecIF:shows Ausschreibungsunterlagen
- SP_KV_MSNS_3_Sammelprojekt-MSNS--Netzauftrag planen SpecIF:shows SAP (NeMo)
- SP_KV_MSNS_3_Sammelprojekt-MSNS--Netzauftrag planen SpecIF:shows Ausführungsplan [initial]
- SP_KV_MSNS_3_Sammelprojekt-MSNS--Netzauftrag planen SpecIF:shows Budgetentscheidung
- SP_KV_MSNS_3_Sammelprojekt-MSNS--Netzauftrag planen SpecIF:shows Budgetforderung
- SP_KV_MSNS_3_Sammelprojekt-MSNS--Netzauftrag planen SpecIF:shows SAP
- SP_KV_MSNS_3_Sammelprojekt-MSNS--Netzauftrag planen SpecIF:shows 28:Technisches Konzept nacharbeiten
- SP_KV_MSNS_3_Sammelprojekt-MSNS--Netzauftrag planen SpecIF:shows Netzauftrag ist konzipiert
- SP_KV_MSNS_3_Sammelprojekt-MSNS--Netzauftrag planen SpecIF:shows Joining Exclusive Gateway
- SP_KV_MSNS_3_Sammelprojekt-MSNS--Netzauftrag planen SpecIF:shows 27:Vollständigkeit der Unterlagen und Machbarkeit prüfen
- SP_KV_MSNS_3_Sammelprojekt-MSNS--Netzauftrag planen SpecIF:shows Forking Exclusive Gateway: Prüfung bestanden?
- SP_KV_MSNS_3_Sammelprojekt-MSNS--Netzauftrag planen SpecIF:shows 29:Genehmigungsplan erstellen
- SP_KV_MSNS_3_Sammelprojekt-MSNS--Netzauftrag planen SpecIF:shows Genehmigungen/Leitungsauskünfte erhalten
- SP_KV_MSNS_3_Sammelprojekt-MSNS--Netzauftrag planen SpecIF:shows Netzauftrag ist beauftragt
- SP_KV_MSNS_3_Sammelprojekt-MSNS--Netzauftrag planen SpecIF:shows 35:Bauakte zusammenstellen und beauftragen
- SP_KV_MSNS_3_Sammelprojekt-MSNS--Netzauftrag planen SpecIF:shows Forking Exclusive Gateway: Budget ausreichend?
- SP_KV_MSNS_3_Sammelprojekt-MSNS--Netzauftrag planen SpecIF:shows 33:Über zusätzliches Budget entscheiden
- SP_KV_MSNS_3_Sammelprojekt-MSNS--Netzauftrag planen SpecIF:shows 32:Budget nachfordern
- SP_KV_MSNS_3_Sammelprojekt-MSNS--Netzauftrag planen SpecIF:shows Planung beendet
- SP_KV_MSNS_3_Sammelprojekt-MSNS--Netzauftrag planen SpecIF:shows Forking Exclusive Gateway: Zusätzliches Budget genehmigt?
- SP_KV_MSNS_3_Sammelprojekt-MSNS--Netzauftrag planen SpecIF:shows 34:Ausschreibung begleiten oder Abruf aus Rahmenvertrag
- SP_KV_MSNS_3_Sammelprojekt-MSNS--Netzauftrag planen SpecIF:shows Joining Exclusive Gateway
- SP_KV_MSNS_3_Sammelprojekt-MSNS--Netzauftrag planen SpecIF:shows 31:MuF kalkulieren und Budget prüfen
- SP_KV_MSNS_3_Sammelprojekt-MSNS--Netzauftrag planen SpecIF:shows 30:Ausführungsplan erstellen
- SP_KV_MSNS_3_Sammelprojekt-MSNS--Netzauftrag planen SpecIF:shows Weiter an Genehmigungsplanung
- SP_KV_MSNS_3_Sammelprojekt-MSNS--Netzauftrag planen SpecIF:shows Zurück an Konzeption
- SP_KV_MSNS_3_Sammelprojekt-MSNS--Netzauftrag planen SpecIF:shows Ja
- SP_KV_MSNS_3_Sammelprojekt-MSNS--Netzauftrag planen SpecIF:shows Ja
- SP_KV_MSNS_3_Sammelprojekt-MSNS--Netzauftrag planen SpecIF:shows Nein
- SP_KV_MSNS_3_Sammelprojekt-MSNS--Netzauftrag planen SpecIF:shows Nein
- Sammelprojekt-MS/NS--Netzauftrag ausführen SpecIF:contains Asset Service - Bauleitung
- Sammelprojekt-MS/NS--Netzauftrag ausführen SpecIF:contains Asset Service - Planung
- Netzauftrag ist beauftragt SpecIF:writes Bauakte
- Asset Service - Bauleitung SpecIF:contains Netzauftrag ist beauftragt
- Asset Service - Bauleitung SpecIF:contains Zurück an Konzeption/Planung
- 36:Bauakte prüfen SpecIF:reads Bauakte
- 36:Bauakte prüfen SpecIF:writes Bauakte [angenommen]
- 36:Bauakte prüfen SpecIF:writes Bauakte [bemängelt]
- Asset Service - Bauleitung SpecIF:contains 36:Bauakte prüfen
- 38:Bedingungen vor Ort prüfen SpecIF:reads Bauakte [angenommen]
- 38:Bedingungen vor Ort prüfen SpecIF:writes Bauakte [final_geprüft]
- Asset Service - Bauleitung SpecIF:contains 38:Bedingungen vor Ort prüfen
- 37:Bauakte nacharbeiten SpecIF:reads Bauakte [bemängelt]
- 37:Bauakte nacharbeiten SpecIF:writes Bauakte
- Asset Service - Planung SpecIF:contains 37:Bauakte nacharbeiten
- 39:Abruf aus Rahmenvertr. und/oder Ausschreibung durchführen SpecIF:reads Bauakte [final_geprüft]
- 39:Abruf aus Rahmenvertr. und/oder Ausschreibung durchführen SpecIF:reads FFM
- 39:Abruf aus Rahmenvertr. und/oder Ausschreibung durchführen SpecIF:reads SAP (NeMo)
- 39:Abruf aus Rahmenvertr. und/oder Ausschreibung durchführen SpecIF:reads AVA
- 39:Abruf aus Rahmenvertr. und/oder Ausschreibung durchführen SpecIF:writes ausgew. Firma/Firmen
- 39:Abruf aus Rahmenvertr. und/oder Ausschreibung durchführen SpecIF:writes FFM
- 39:Abruf aus Rahmenvertr. und/oder Ausschreibung durchführen SpecIF:writes SAP (NeMo)
- 39:Abruf aus Rahmenvertr. und/oder Ausschreibung durchführen SpecIF:writes AVA
- 39:Abruf aus Rahmenvertr. und/oder Ausschreibung durchführen SpecIF:writes Dienstleister-Portal
- Asset Service - Bauleitung SpecIF:contains 39:Abruf aus Rahmenvertr. und/oder Ausschreibung durchführen
- 40:Baubeginn abstimmen SpecIF:reads ausgew. Firma/Firmen
- 40:Baubeginn abstimmen SpecIF:writes AVA
- 40:Baubeginn abstimmen SpecIF:writes Felix
- 40:Baubeginn abstimmen SpecIF:writes SAP
- 40:Baubeginn abstimmen SpecIF:writes Dienstleister-Portal
- Asset Service - Bauleitung SpecIF:contains 40:Baubeginn abstimmen
- 42:Kabelmontage beauftragen SpecIF:reads Bauakte [final_geprüft]
- 42:Kabelmontage beauftragen SpecIF:writes Montageauftrag [erteilt]
- Asset Service - Bauleitung SpecIF:contains 42:Kabelmontage beauftragen
- 41:Ausführung überwachen (intern oder extern) SpecIF:reads Bauakte [final_geprüft]
- 41:Ausführung überwachen (intern oder extern) SpecIF:writes Baustellen-Begehungs-Protokoll
- Asset Service - Bauleitung SpecIF:contains 41:Ausführung überwachen (intern oder extern)
- 43:Aufmaß prüfen SpecIF:reads Leistungserfassungsblatt
- 43:Aufmaß prüfen SpecIF:reads AVA
- 43:Aufmaß prüfen SpecIF:reads Felix
- 43:Aufmaß prüfen SpecIF:reads SAP
- 43:Aufmaß prüfen SpecIF:reads Dienstleister-Portal
- 43:Aufmaß prüfen SpecIF:writes Leistungserfassungsblatt [bestätigt]
- Asset Service - Bauleitung SpecIF:contains 43:Aufmaß prüfen
- Netzauftrag ausgeführt SpecIF:reads Bauakte [abgeschlossen]
- Asset Service - Bauleitung SpecIF:contains Netzauftrag ausgeführt
- 45:Netzauftrag abschließen SpecIF:reads Bauakte [final_geprüft]
- 45:Netzauftrag abschließen SpecIF:writes Bauakte [abgeschlossen]
- Asset Service - Bauleitung SpecIF:contains 45:Netzauftrag abschließen
- 44:Ist-Doku kontrollieren und an NIS weiterleiten & archivieren SpecIF:reads Vermessungszeichnung (Aufmaß)
- 44:Ist-Doku kontrollieren und an NIS weiterleiten & archivieren SpecIF:reads Netzveränderung
- 44:Ist-Doku kontrollieren und an NIS weiterleiten & archivieren SpecIF:writes PlanIT (NIS)
- 44:Ist-Doku kontrollieren und an NIS weiterleiten & archivieren SpecIF:writes ADMS
- 44:Ist-Doku kontrollieren und an NIS weiterleiten & archivieren SpecIF:writes Sachdatenportal
- Asset Service - Bauleitung SpecIF:contains 44:Ist-Doku kontrollieren und an NIS weiterleiten & archivieren
- Forking Exclusive Gateway: Bauausführung möglich? SpecIF:signals Ja
- Ja SpecIF:triggers 39:Abruf aus Rahmenvertr. und/oder Ausschreibung durchführen
- Forking Exclusive Gateway: Bauausführung möglich? SpecIF:signals Nein
- Nein SpecIF:triggers Zurück an Konzeption/Planung
- 38:Bedingungen vor Ort prüfen SpecIF:precedes Forking Exclusive Gateway
- Forking Exclusive Gateway: Prüfung bestanden? SpecIF:signals Ja
- Ja SpecIF:triggers 38:Bedingungen vor Ort prüfen
- 36:Bauakte prüfen SpecIF:precedes Forking Exclusive Gateway: Prüfung bestanden?
- Joining Exclusive Gateway SpecIF:precedes 36:Bauakte prüfen
- 37:Bauakte nacharbeiten SpecIF:precedes Joining Exclusive Gateway
- Forking Exclusive Gateway: Prüfung bestanden? SpecIF:signals Nein
- Nein SpecIF:triggers 37:Bauakte nacharbeiten
- Netzauftrag ist beauftragt SpecIF:triggers Joining Exclusive Gateway
- 39:Abruf aus Rahmenvertr. und/oder Ausschreibung durchführen SpecIF:precedes 40:Baubeginn abstimmen
- 40:Baubeginn abstimmen SpecIF:precedes Forking Inclusive Gateway: Ist Kabelmontage und/oder Tiefbau erforderlich?
- Forking Inclusive Gateway: Ist Kabelmontage und/oder Tiefbau erforderlich? SpecIF:signals Kabelmontage
- Kabelmontage SpecIF:triggers 42:Kabelmontage beauftragen
- Forking Inclusive Gateway: Ist Kabelmontage und/oder Tiefbau erforderlich? SpecIF:signals Tiefbau
- Tiefbau SpecIF:triggers 41:Ausführung überwachen (intern oder extern)
- 42:Kabelmontage beauftragen SpecIF:precedes Joining Inclusive Gateway
- 41:Ausführung überwachen (intern oder extern) SpecIF:precedes Joining Inclusive Gateway
- Joining Inclusive Gateway SpecIF:precedes 43:Aufmaß prüfen
- 43:Aufmaß prüfen SpecIF:precedes 44:Ist-Doku kontrollieren und an NIS weiterleiten & archivieren
- 45:Netzauftrag abschließen SpecIF:signals Netzauftrag ausgeführt
- 44:Ist-Doku kontrollieren und an NIS weiterleiten & archivieren SpecIF:precedes 45:Netzauftrag abschließen
- Text Annotation 01 SpecIF:refersTo Netzauftrag ist beauftragt
- Text Annotation 02 SpecIF:refersTo FFM
- Text Annotation 03 SpecIF:refersTo Dienstleister-Portal
- Text Annotation 03 SpecIF:refersTo SAP
- Text Annotation 03 SpecIF:refersTo Felix
- Text Annotation 03 SpecIF:refersTo AVA
- Text Annotation 04 SpecIF:refersTo Baustellen-Begehungs-Protokoll
- Text Annotation 05 SpecIF:refersTo Leistungserfassungsblatt [bestätigt]
- Text Annotation 06 SpecIF:refersTo 39:Abruf aus Rahmenvertr. und/oder Ausschreibung durchführen
- Text Annotation 07 SpecIF:refersTo 43:Aufmaß prüfen
- Text Annotation 08 SpecIF:refersTo 45:Netzauftrag abschließen
- SP_KV_MSNS_4_Sammelprojekt-MSNS--Netzauftrag ausführen SpecIF:shows Sammelprojekt-MS/NS--Netzauftrag ausführen
- SP_KV_MSNS_4_Sammelprojekt-MSNS--Netzauftrag ausführen SpecIF:shows Asset Service - Bauleitung
- SP_KV_MSNS_4_Sammelprojekt-MSNS--Netzauftrag ausführen SpecIF:shows Asset Service - Planung
- SP_KV_MSNS_4_Sammelprojekt-MSNS--Netzauftrag ausführen SpecIF:shows Bauakte [bemängelt]
- SP_KV_MSNS_4_Sammelprojekt-MSNS--Netzauftrag ausführen SpecIF:shows Bauakte
- SP_KV_MSNS_4_Sammelprojekt-MSNS--Netzauftrag ausführen SpecIF:shows Bauakte [angenommen]
- SP_KV_MSNS_4_Sammelprojekt-MSNS--Netzauftrag ausführen SpecIF:shows Bauakte [final_geprüft]
- SP_KV_MSNS_4_Sammelprojekt-MSNS--Netzauftrag ausführen SpecIF:shows SAP (NeMo)
- SP_KV_MSNS_4_Sammelprojekt-MSNS--Netzauftrag ausführen SpecIF:shows AVA
- SP_KV_MSNS_4_Sammelprojekt-MSNS--Netzauftrag ausführen SpecIF:shows FFM
- SP_KV_MSNS_4_Sammelprojekt-MSNS--Netzauftrag ausführen SpecIF:shows ausgew. Firma/Firmen
- SP_KV_MSNS_4_Sammelprojekt-MSNS--Netzauftrag ausführen SpecIF:shows Dienstleister-Portal
- SP_KV_MSNS_4_Sammelprojekt-MSNS--Netzauftrag ausführen SpecIF:shows Montageauftrag [erteilt]
- SP_KV_MSNS_4_Sammelprojekt-MSNS--Netzauftrag ausführen SpecIF:shows Baustellen-Begehungs-Protokoll
- SP_KV_MSNS_4_Sammelprojekt-MSNS--Netzauftrag ausführen SpecIF:shows Leistungserfassungsblatt
- SP_KV_MSNS_4_Sammelprojekt-MSNS--Netzauftrag ausführen SpecIF:shows SAP
- SP_KV_MSNS_4_Sammelprojekt-MSNS--Netzauftrag ausführen SpecIF:shows Felix
- SP_KV_MSNS_4_Sammelprojekt-MSNS--Netzauftrag ausführen SpecIF:shows Leistungserfassungsblatt [bestätigt]
- SP_KV_MSNS_4_Sammelprojekt-MSNS--Netzauftrag ausführen SpecIF:shows Bauakte [abgeschlossen]
- SP_KV_MSNS_4_Sammelprojekt-MSNS--Netzauftrag ausführen SpecIF:shows PlanIT (NIS)
- SP_KV_MSNS_4_Sammelprojekt-MSNS--Netzauftrag ausführen SpecIF:shows Sachdatenportal
- SP_KV_MSNS_4_Sammelprojekt-MSNS--Netzauftrag ausführen SpecIF:shows ADMS
- SP_KV_MSNS_4_Sammelprojekt-MSNS--Netzauftrag ausführen SpecIF:shows Netzveränderung
- SP_KV_MSNS_4_Sammelprojekt-MSNS--Netzauftrag ausführen SpecIF:shows Vermessungszeichnung (Aufmaß)
- SP_KV_MSNS_4_Sammelprojekt-MSNS--Netzauftrag ausführen SpecIF:shows Netzauftrag ist beauftragt
- SP_KV_MSNS_4_Sammelprojekt-MSNS--Netzauftrag ausführen SpecIF:shows Joining Exclusive Gateway
- SP_KV_MSNS_4_Sammelprojekt-MSNS--Netzauftrag ausführen SpecIF:shows Forking Exclusive Gateway: Prüfung bestanden?
- SP_KV_MSNS_4_Sammelprojekt-MSNS--Netzauftrag ausführen SpecIF:shows Zurück an Konzeption/Planung
- SP_KV_MSNS_4_Sammelprojekt-MSNS--Netzauftrag ausführen SpecIF:shows Forking Exclusive Gateway
- SP_KV_MSNS_4_Sammelprojekt-MSNS--Netzauftrag ausführen SpecIF:shows Forking Exclusive Gateway: Bauausführung möglich?
- SP_KV_MSNS_4_Sammelprojekt-MSNS--Netzauftrag ausführen SpecIF:shows 36:Bauakte prüfen
- SP_KV_MSNS_4_Sammelprojekt-MSNS--Netzauftrag ausführen SpecIF:shows 38:Bedingungen vor Ort prüfen
- SP_KV_MSNS_4_Sammelprojekt-MSNS--Netzauftrag ausführen SpecIF:shows 37:Bauakte nacharbeiten
- SP_KV_MSNS_4_Sammelprojekt-MSNS--Netzauftrag ausführen SpecIF:shows 39:Abruf aus Rahmenvertr. und/oder Ausschreibung durchführen
- SP_KV_MSNS_4_Sammelprojekt-MSNS--Netzauftrag ausführen SpecIF:shows Forking Inclusive Gateway: Ist Kabelmontage und/oder Tiefbau erforderlich?
- SP_KV_MSNS_4_Sammelprojekt-MSNS--Netzauftrag ausführen SpecIF:shows 40:Baubeginn abstimmen
- SP_KV_MSNS_4_Sammelprojekt-MSNS--Netzauftrag ausführen SpecIF:shows 42:Kabelmontage beauftragen
- SP_KV_MSNS_4_Sammelprojekt-MSNS--Netzauftrag ausführen SpecIF:shows 41:Ausführung überwachen (intern oder extern)
- SP_KV_MSNS_4_Sammelprojekt-MSNS--Netzauftrag ausführen SpecIF:shows Joining Inclusive Gateway
- SP_KV_MSNS_4_Sammelprojekt-MSNS--Netzauftrag ausführen SpecIF:shows 43:Aufmaß prüfen
- SP_KV_MSNS_4_Sammelprojekt-MSNS--Netzauftrag ausführen SpecIF:shows Netzauftrag ausgeführt
- SP_KV_MSNS_4_Sammelprojekt-MSNS--Netzauftrag ausführen SpecIF:shows 45:Netzauftrag abschließen
- SP_KV_MSNS_4_Sammelprojekt-MSNS--Netzauftrag ausführen SpecIF:shows 44:Ist-Doku kontrollieren und an NIS weiterleiten & archivieren
- SP_KV_MSNS_4_Sammelprojekt-MSNS--Netzauftrag ausführen SpecIF:shows Ja
- SP_KV_MSNS_4_Sammelprojekt-MSNS--Netzauftrag ausführen SpecIF:shows Nein
- SP_KV_MSNS_4_Sammelprojekt-MSNS--Netzauftrag ausführen SpecIF:shows Ja
- SP_KV_MSNS_4_Sammelprojekt-MSNS--Netzauftrag ausführen SpecIF:shows Nein
- SP_KV_MSNS_4_Sammelprojekt-MSNS--Netzauftrag ausführen SpecIF:shows Kabelmontage
- SP_KV_MSNS_4_Sammelprojekt-MSNS--Netzauftrag ausführen SpecIF:shows Tiefbau
- UST_AVA/Typicals_0001 - Bauvorhaben (Projekt) anlegen IREB:refines 45:Projektinfrastruktur anlegen
- UST_AVA/Typicals_0001 - Bauvorhaben (Projekt) anlegen IREB:refines 11:Netzauftrag anlegen
- UST_AVA/Typicals_0001 - Bauvorhaben (Projekt) anlegen IREB:refines 20:Netzauftrag anlegen
- UST_AVA/Typicals_0002 - LV konfigurieren IREB:refines 49:Leistungen konkretisieren
- UST_AVA/Typicals_0002 - LV konfigurieren IREB:refines 12:Technisches Konzept erstellen
- UST_AVA/Typicals_0003 - Kostenzuordnung festlegen IREB:refines 49:Leistungen konkretisieren
- UST_AVA/Typicals_0003 - Kostenzuordnung festlegen IREB:refines 12:Technisches Konzept erstellen
- UST_AVA/Typicals_0004 - Leistungsbeschreibung spezifizieren IREB:refines 59:Vergabe vorbereiten
- UST_AVA/Typicals_0004 - Leistungsbeschreibung spezifizieren IREB:refines 30:Ausführungsplan erstellen
- UST_AVA/Typicals_0004 - Leistungsbeschreibung spezifizieren IREB:refines 31:MuF kalkulieren und Budget prüfen
- UST_AVA/Typicals_0005 - Abrufbestellung aus RV anlegen, Bestellanforderungen zum RV anlegen, Normalbestellung anlegen IREB:refines 70:Vergabeeinheit aus Liste auswählen und BANFen erstellen
- UST_AVA/Typicals_0005 - Abrufbestellung aus RV anlegen, Bestellanforderungen zum RV anlegen, Normalbestellung anlegen IREB:refines 29:Genehmigungsplan erstellen
- UST_AVA/Typicals_0005 - Abrufbestellung aus RV anlegen, Bestellanforderungen zum RV anlegen, Normalbestellung anlegen IREB:refines 39:Abruf aus Rahmenvertr. und/oder Ausschreibung durchführen
- UST_AVA/Typicals_0006 - Selektierte Informationen mit Dritten (Bietern) austauschen IREB:refines 71:Beschaffungsprozess
- UST_AVA/Typicals_0007 - Angebote vergleichen IREB:refines 71:Beschaffungsprozess
- UST_AVA/Typicals_0008 - Vergabevertag vorbereiten IREB:refines 71:Beschaffungsprozess
- UST_AVA/Typicals_0010 - Vertragsfirmen beauftragen IREB:refines 29:Genehmigungsplan erstellen
- UST_AVA/Typicals_0010 - Vertragsfirmen beauftragen IREB:refines 39:Abruf aus Rahmenvertr. und/oder Ausschreibung durchführen
- UST_AVA/Typicals_0011 - IST-Leistungen durch Auftragnehmer erfassen IREB:refines 65:Bauüberwachung durchführen
- UST_AVA/Typicals_0011 - IST-Leistungen durch Auftragnehmer erfassen IREB:refines 29:Genehmigungsplan erstellen
- UST_AVA/Typicals_0011 - IST-Leistungen durch Auftragnehmer erfassen IREB:refines 43:Aufmaß prüfen
- UST_AVA/Typicals_0012 - Aufmaß / IST-Leistung durch AG prüfen IREB:refines 65:Bauüberwachung durchführen
- UST_AVA/Typicals_0012 - Aufmaß / IST-Leistung durch AG prüfen IREB:refines 29:Genehmigungsplan erstellen
- UST_AVA/Typicals_0012 - Aufmaß / IST-Leistung durch AG prüfen IREB:refines 43:Aufmaß prüfen
- UST_AVA/Typicals_0013 - IST-Leistungen durch AN bestätigen / abnehmen IREB:refines 65:Bauüberwachung durchführen
- UST_AVA/Typicals_0013 - IST-Leistungen durch AN bestätigen / abnehmen IREB:refines 29:Genehmigungsplan erstellen
- UST_AVA/Typicals_0013 - IST-Leistungen durch AN bestätigen / abnehmen IREB:refines 43:Aufmaß prüfen
- UST_AVA/Typicals_0014 - Rechnungsprüfung IREB:refines 65:Bauüberwachung durchführen
- UST_AVA/Typicals_0014 - Rechnungsprüfung IREB:refines 29:Genehmigungsplan erstellen
- UST_AVA/Typicals_0014 - Rechnungsprüfung IREB:refines 43:Aufmaß prüfen
- UST_AVA/Typicals_0015 - Zahlvorgang anstoßen + bearbeiten IREB:refines 65:Bauüberwachung durchführen
- UST_AVA/Typicals_0015 - Zahlvorgang anstoßen + bearbeiten IREB:refines 29:Genehmigungsplan erstellen
- UST_AVA/Typicals_0015 - Zahlvorgang anstoßen + bearbeiten IREB:refines 43:Aufmaß prüfen
- UST_AVA/Typicals_0016 - Kosten/Leistungs-SOLL-IST-Abgleich durchführen IREB:refines 69:Lessons Learned übertragen
- UST_AVA/Typicals_0017 - Auswertkriterien festlegen IREB:refines 69:Lessons Learned übertragen
- UST_AVA/Typicals_0018 - Titel IREB:refines 10:Projektkategorie und Projekttyp ermitteln
- UST_AVA/Typicals_0022 - Projektspezifisches Leistungsverzeichnis erstellen IREB:refines 59:Vergabe vorbereiten
- UST_AVA/Typicals_0023 - Suchfunktion in TBs und Richtlinien IREB:refines 59:Vergabe vorbereiten
- REQ_AVA/Typicals_100 - 'Titel' oslc_rm:satisfiedBy UST_AVA/Typicals_0010 - Vertragsfirmen beauftragen
- REQ_AVA/Typicals_101 - 'Titel' oslc_rm:satisfiedBy UST_AVA/Typicals_0017 - Auswertkriterien festlegen
- REQ_AVA/Typicals_102 - 'Titel' oslc_rm:satisfiedBy UST_AVA/Typicals_0009 - Vergabevertrag abschließen
- REQ_AVA/Typicals_103 - 'Titel' oslc_rm:satisfiedBy UST_AVA/Typicals_0002 - LV konfigurieren
- REQ_AVA/Typicals_104 - 'Titel' oslc_rm:satisfiedBy UST_AVA/Typicals_0004 - Leistungsbeschreibung spezifizieren
- REQ_AVA/Typicals_105 - 'Titel' oslc_rm:satisfiedBy UST_AVA/Typicals_0006 - Selektierte Informationen mit Dritten (Bietern) austauschen
- REQ_AVA/Typicals_107 - 'Titel' oslc_rm:satisfiedBy UST_AVA/Typicals_0002 - LV konfigurieren
- REQ_AVA/Typicals_108 - 'Titel' oslc_rm:satisfiedBy UST_AVA/Typicals_0006 - Selektierte Informationen mit Dritten (Bietern) austauschen
- REQ_AVA/Typicals_110 - 'Titel' oslc_rm:satisfiedBy UST_AVA/Typicals_0004 - Leistungsbeschreibung spezifizieren
- REQ_AVA/Typicals_114 - 'Titel' oslc_rm:satisfiedBy UST_AVA/Typicals_0004 - Leistungsbeschreibung spezifizieren
- REQ_AVA/Typicals_115 - 'Titel' oslc_rm:satisfiedBy UST_AVA/Typicals_0001 - Bauvorhaben (Projekt) anlegen
- REQ_AVA/Typicals_117 - 'Titel' oslc_rm:satisfiedBy UST_AVA/Typicals_0002 - LV konfigurieren
- REQ_AVA/Typicals_118 - 'Titel' oslc_rm:satisfiedBy UST_AVA/Typicals_0017 - Auswertkriterien festlegen
- REQ_AVA/Typicals_119 - 'Titel' oslc_rm:satisfiedBy UST_AVA/Typicals_0002 - LV konfigurieren
- REQ_AVA/Typicals_12 - 'Titel' oslc_rm:satisfiedBy UST_AVA/Typicals_0001 - Bauvorhaben (Projekt) anlegen
- REQ_AVA/Typicals_122 - 'Titel' oslc_rm:satisfiedBy UST_AVA/Typicals_0002 - LV konfigurieren
- REQ_AVA/Typicals_124 - 'Titel' oslc_rm:satisfiedBy UST_AVA/Typicals_0002 - LV konfigurieren
- REQ_AVA/Typicals_125 - 'Titel' oslc_rm:satisfiedBy UST_AVA/Typicals_0004 - Leistungsbeschreibung spezifizieren
- REQ_AVA/Typicals_126 - 'Titel' oslc_rm:satisfiedBy UST_AVA/Typicals_0004 - Leistungsbeschreibung spezifizieren
- REQ_AVA/Typicals_128 - 'Titel' oslc_rm:satisfiedBy UST_AVA/Typicals_0002 - LV konfigurieren
- REQ_AVA/Typicals_130 - 'Titel' oslc_rm:satisfiedBy UST_AVA/Typicals_0006 - Selektierte Informationen mit Dritten (Bietern) austauschen
- REQ_AVA/Typicals_133 - 'Titel' oslc_rm:satisfiedBy UST_AVA/Typicals_0009 - Vergabevertrag abschließen
- REQ_AVA/Typicals_135 - 'Titel' oslc_rm:satisfiedBy UST_AVA/Typicals_0012 - Aufmaß / IST-Leistung durch AG prüfen
- REQ_AVA/Typicals_136 - 'Titel' oslc_rm:satisfiedBy UST_AVA/Typicals_0014 - Rechnungsprüfung
- REQ_AVA/Typicals_139 - 'Titel' oslc_rm:satisfiedBy UST_AVA/Typicals_0012 - Aufmaß / IST-Leistung durch AG prüfen
- REQ_AVA/Typicals_140 - 'Titel' oslc_rm:satisfiedBy UST_AVA/Typicals_0016 - Kosten/Leistungs-SOLL-IST-Abgleich durchführen
- REQ_AVA/Typicals_141 - 'Titel' oslc_rm:satisfiedBy UST_AVA/Typicals_0004 - Leistungsbeschreibung spezifizieren
- REQ_AVA/Typicals_143 - 'Titel' oslc_rm:satisfiedBy UST_AVA/Typicals_0002 - LV konfigurieren
- REQ_AVA/Typicals_144 - 'Titel' oslc_rm:satisfiedBy UST_AVA/Typicals_0002 - LV konfigurieren
- REQ_AVA/Typicals_145 - 'Titel' oslc_rm:satisfiedBy UST_AVA/Typicals_0010 - Vertragsfirmen beauftragen
- REQ_AVA/Typicals_147 - 'Titel' oslc_rm:satisfiedBy UST_AVA/Typicals_0002 - LV konfigurieren
- REQ_AVA/Typicals_148 - 'Titel' oslc_rm:satisfiedBy UST_AVA/Typicals_0006 - Selektierte Informationen mit Dritten (Bietern) austauschen
- REQ_AVA/Typicals_149 - 'Titel' oslc_rm:satisfiedBy UST_AVA/Typicals_0002 - LV konfigurieren
- REQ_AVA/Typicals_15 - 'Titel' oslc_rm:satisfiedBy UST_AVA/Typicals_0001 - Bauvorhaben (Projekt) anlegen
- REQ_AVA/Typicals_151 - 'Titel' oslc_rm:satisfiedBy UST_AVA/Typicals_0016 - Kosten/Leistungs-SOLL-IST-Abgleich durchführen
- REQ_AVA/Typicals_152 - 'Titel' oslc_rm:satisfiedBy UST_AVA/Typicals_0002 - LV konfigurieren
- REQ_AVA/Typicals_154 - 'Titel' oslc_rm:satisfiedBy UST_AVA/Typicals_0002 - LV konfigurieren
- REQ_AVA/Typicals_158 - 'Titel' oslc_rm:satisfiedBy UST_AVA/Typicals_0002 - LV konfigurieren
- REQ_AVA/Typicals_159 - 'Titel' oslc_rm:satisfiedBy UST_AVA/Typicals_0002 - LV konfigurieren
- REQ_AVA/Typicals_160 - 'Titel' oslc_rm:satisfiedBy UST_AVA/Typicals_0002 - LV konfigurieren
- REQ_AVA/Typicals_161 - 'Titel' oslc_rm:satisfiedBy UST_AVA/Typicals_0011 - IST-Leistungen durch Auftragnehmer erfassen
- REQ_AVA/Typicals_165 - 'Titel' oslc_rm:satisfiedBy UST_AVA/Typicals_0002 - LV konfigurieren
- REQ_AVA/Typicals_165.1 - 'Titel' oslc_rm:satisfiedBy UST_AVA/Typicals_0002 - LV konfigurieren
- REQ_AVA/Typicals_165.3 - 'Titel' oslc_rm:satisfiedBy UST_AVA/Typicals_0002 - LV konfigurieren
- REQ_AVA/Typicals_165.4 - 'Titel' oslc_rm:satisfiedBy UST_AVA/Typicals_0002 - LV konfigurieren
- REQ_AVA/Typicals_165.5 - 'Titel' oslc_rm:satisfiedBy UST_AVA/Typicals_0002 - LV konfigurieren
- REQ_AVA/Typicals_165.6 - 'Titel' oslc_rm:satisfiedBy UST_AVA/Typicals_0002 - LV konfigurieren
- REQ_AVA/Typicals_166 - 'Titel' oslc_rm:satisfiedBy UST_AVA/Typicals_0003 - Kostenzuordnung festlegen
- REQ_AVA/Typicals_166.1 - 'Titel' oslc_rm:satisfiedBy UST_AVA/Typicals_0003 - Kostenzuordnung festlegen
- REQ_AVA/Typicals_166.2 - 'Titel' oslc_rm:satisfiedBy UST_AVA/Typicals_0003 - Kostenzuordnung festlegen
- REQ_AVA/Typicals_167 - 'Titel' oslc_rm:satisfiedBy UST_AVA/Typicals_0013 - IST-Leistungen durch AN bestätigen / abnehmen
- REQ_AVA/Typicals_167.1 - 'Titel' oslc_rm:satisfiedBy UST_AVA/Typicals_0013 - IST-Leistungen durch AN bestätigen / abnehmen
- REQ_AVA/Typicals_167.2 - 'Titel' oslc_rm:satisfiedBy UST_AVA/Typicals_0013 - IST-Leistungen durch AN bestätigen / abnehmen
- REQ_AVA/Typicals_168 - 'Titel' oslc_rm:satisfiedBy UST_AVA/Typicals_0004 - Leistungsbeschreibung spezifizieren
- REQ_AVA/Typicals_169 - 'Titel' oslc_rm:satisfiedBy UST_AVA/Typicals_0004 - Leistungsbeschreibung spezifizieren
- REQ_AVA/Typicals_17 - 'Titel' oslc_rm:satisfiedBy UST_AVA/Typicals_0017 - Auswertkriterien festlegen
- REQ_AVA/Typicals_170 - 'Titel' oslc_rm:satisfiedBy UST_AVA/Typicals_0004 - Leistungsbeschreibung spezifizieren
- REQ_AVA/Typicals_171 - 'Titel' oslc_rm:satisfiedBy UST_AVA/Typicals_0004 - Leistungsbeschreibung spezifizieren
- REQ_AVA/Typicals_172 - 'Titel' oslc_rm:satisfiedBy UST_AVA/Typicals_0004 - Leistungsbeschreibung spezifizieren
- REQ_AVA/Typicals_173 - 'Titel' oslc_rm:satisfiedBy UST_AVA/Typicals_0004 - Leistungsbeschreibung spezifizieren
- REQ_AVA/Typicals_174 - 'Titel' oslc_rm:satisfiedBy UST_AVA/Typicals_0004 - Leistungsbeschreibung spezifizieren
- REQ_AVA/Typicals_175 - 'Titel' oslc_rm:satisfiedBy UST_AVA/Typicals_0004 - Leistungsbeschreibung spezifizieren
- REQ_AVA/Typicals_176 - 'Titel' oslc_rm:satisfiedBy UST_AVA/Typicals_0004 - Leistungsbeschreibung spezifizieren
- REQ_AVA/Typicals_177 - 'Titel' oslc_rm:satisfiedBy UST_AVA/Typicals_0004 - Leistungsbeschreibung spezifizieren
- REQ_AVA/Typicals_178 - 'Titel' oslc_rm:satisfiedBy UST_AVA/Typicals_0002 - LV konfigurieren
- REQ_AVA/Typicals_179 - 'Titel' oslc_rm:satisfiedBy UST_AVA/Typicals_0006 - Selektierte Informationen mit Dritten (Bietern) austauschen
- REQ_AVA/Typicals_18 - 'Titel' oslc_rm:satisfiedBy UST_AVA/Typicals_0003 - Kostenzuordnung festlegen
- REQ_AVA/Typicals_180 - 'Titel' oslc_rm:satisfiedBy UST_AVA/Typicals_0002 - LV konfigurieren
- REQ_AVA/Typicals_181 - 'Titel' oslc_rm:satisfiedBy UST_AVA/Typicals_0007 - Angebote vergleichen
- REQ_AVA/Typicals_182 - 'Titel' oslc_rm:satisfiedBy UST_AVA/Typicals_0009 - Vergabevertrag abschließen
- REQ_AVA/Typicals_183 - 'Titel' oslc_rm:satisfiedBy UST_AVA/Typicals_0010 - Vertragsfirmen beauftragen
- REQ_AVA/Typicals_184 - 'Titel' oslc_rm:satisfiedBy UST_AVA/Typicals_0010 - Vertragsfirmen beauftragen
- REQ_AVA/Typicals_185 - 'Titel' oslc_rm:satisfiedBy UST_AVA/Typicals_0013 - IST-Leistungen durch AN bestätigen / abnehmen
- REQ_AVA/Typicals_186 - 'Titel' oslc_rm:satisfiedBy UST_AVA/Typicals_0013 - IST-Leistungen durch AN bestätigen / abnehmen
- REQ_AVA/Typicals_187 - 'Titel' oslc_rm:satisfiedBy UST_AVA/Typicals_0013 - IST-Leistungen durch AN bestätigen / abnehmen
- REQ_AVA/Typicals_189 - 'Titel' oslc_rm:satisfiedBy UST_AVA/Typicals_0016 - Kosten/Leistungs-SOLL-IST-Abgleich durchführen
- REQ_AVA/Typicals_190 - 'Titel' oslc_rm:satisfiedBy UST_AVA/Typicals_0006 - Selektierte Informationen mit Dritten (Bietern) austauschen
- REQ_AVA/Typicals_191 - 'Titel' oslc_rm:satisfiedBy UST_AVA/Typicals_0006 - Selektierte Informationen mit Dritten (Bietern) austauschen
- REQ_AVA/Typicals_20 - 'Titel' oslc_rm:satisfiedBy UST_AVA/Typicals_0002 - LV konfigurieren
- REQ_AVA/Typicals_21 - 'Titel' oslc_rm:satisfiedBy UST_AVA/Typicals_0002 - LV konfigurieren
- REQ_AVA/Typicals_22 - 'Titel' oslc_rm:satisfiedBy UST_AVA/Typicals_0016 - Kosten/Leistungs-SOLL-IST-Abgleich durchführen
- REQ_AVA/Typicals_25 - 'Titel' oslc_rm:satisfiedBy UST_AVA/Typicals_0016 - Kosten/Leistungs-SOLL-IST-Abgleich durchführen
- REQ_AVA/Typicals_26 - 'Titel' oslc_rm:satisfiedBy UST_AVA/Typicals_0016 - Kosten/Leistungs-SOLL-IST-Abgleich durchführen
- REQ_AVA/Typicals_29 - 'Titel' oslc_rm:satisfiedBy UST_AVA/Typicals_0004 - Leistungsbeschreibung spezifizieren
- REQ_AVA/Typicals_35 - 'Titel' oslc_rm:satisfiedBy UST_AVA/Typicals_0002 - LV konfigurieren
- REQ_AVA/Typicals_36 - 'Titel' oslc_rm:satisfiedBy UST_AVA/Typicals_0007 - Angebote vergleichen
- REQ_AVA/Typicals_37 - 'Titel' oslc_rm:satisfiedBy UST_AVA/Typicals_0003 - Kostenzuordnung festlegen
- REQ_AVA/Typicals_4 - 'Titel' oslc_rm:satisfiedBy UST_AVA/Typicals_0002 - LV konfigurieren
- REQ_AVA/Typicals_42 - 'Titel' oslc_rm:satisfiedBy UST_AVA/Typicals_0001 - Bauvorhaben (Projekt) anlegen
- REQ_AVA/Typicals_43 - 'Titel' oslc_rm:satisfiedBy UST_AVA/Typicals_0002 - LV konfigurieren
- REQ_AVA/Typicals_44 - 'Titel' oslc_rm:satisfiedBy UST_AVA/Typicals_0002 - LV konfigurieren
- REQ_AVA/Typicals_45 - 'Titel' oslc_rm:satisfiedBy UST_AVA/Typicals_0003 - Kostenzuordnung festlegen
- REQ_AVA/Typicals_46 - 'Titel' oslc_rm:satisfiedBy UST_AVA/Typicals_0002 - LV konfigurieren
- REQ_AVA/Typicals_47 - 'Titel' oslc_rm:satisfiedBy UST_AVA/Typicals_0002 - LV konfigurieren
- REQ_AVA/Typicals_49 - 'Titel' oslc_rm:satisfiedBy UST_AVA/Typicals_0003 - Kostenzuordnung festlegen
- REQ_AVA/Typicals_5 - 'Titel' oslc_rm:satisfiedBy UST_AVA/Typicals_0017 - Auswertkriterien festlegen
- REQ_AVA/Typicals_54 - 'Titel' oslc_rm:satisfiedBy UST_AVA/Typicals_0004 - Leistungsbeschreibung spezifizieren
- REQ_AVA/Typicals_56 - 'Titel' oslc_rm:satisfiedBy UST_AVA/Typicals_0004 - Leistungsbeschreibung spezifizieren
- REQ_AVA/Typicals_57 - 'Titel' oslc_rm:satisfiedBy UST_AVA/Typicals_0004 - Leistungsbeschreibung spezifizieren
- REQ_AVA/Typicals_59 - 'Titel' oslc_rm:satisfiedBy UST_AVA/Typicals_0001 - Bauvorhaben (Projekt) anlegen
- REQ_AVA/Typicals_60.9 - 'Titel' oslc_rm:satisfiedBy UST_AVA/Typicals_0010 - Vertragsfirmen beauftragen
- REQ_AVA/Typicals_62 - 'Titel' oslc_rm:satisfiedBy UST_AVA/Typicals_0001 - Bauvorhaben (Projekt) anlegen
- REQ_AVA/Typicals_66 - 'Titel' oslc_rm:satisfiedBy UST_AVA/Typicals_0001 - Bauvorhaben (Projekt) anlegen
- REQ_AVA/Typicals_67 - 'Titel' oslc_rm:satisfiedBy UST_AVA/Typicals_0008 - Vergabevertag vorbereiten
- REQ_AVA/Typicals_69 - 'Titel' oslc_rm:satisfiedBy UST_AVA/Typicals_0003 - Kostenzuordnung festlegen
- REQ_AVA/Typicals_7 - 'Titel' oslc_rm:satisfiedBy UST_AVA/Typicals_0002 - LV konfigurieren
- REQ_AVA/Typicals_76 - 'Titel' oslc_rm:satisfiedBy UST_AVA/Typicals_0003 - Kostenzuordnung festlegen
- REQ_AVA/Typicals_76.1 - 'Titel' oslc_rm:satisfiedBy UST_AVA/Typicals_0003 - Kostenzuordnung festlegen
- REQ_AVA/Typicals_76.2 - 'Titel' oslc_rm:satisfiedBy UST_AVA/Typicals_0003 - Kostenzuordnung festlegen
- REQ_AVA/Typicals_76.3 - 'Titel' oslc_rm:satisfiedBy UST_AVA/Typicals_0003 - Kostenzuordnung festlegen
- REQ_AVA/Typicals_77 - 'Titel' oslc_rm:satisfiedBy UST_AVA/Typicals_0003 - Kostenzuordnung festlegen
- REQ_AVA/Typicals_78 - 'Titel' oslc_rm:satisfiedBy UST_AVA/Typicals_0001 - Bauvorhaben (Projekt) anlegen
- REQ_AVA/Typicals_80 - 'Titel' oslc_rm:satisfiedBy UST_AVA/Typicals_0003 - Kostenzuordnung festlegen
- REQ_AVA/Typicals_82.1 - 'Titel' oslc_rm:satisfiedBy UST_AVA/Typicals_0002 - LV konfigurieren
- REQ_AVA/Typicals_82.2 - 'Titel' oslc_rm:satisfiedBy UST_AVA/Typicals_0004 - Leistungsbeschreibung spezifizieren
- REQ_AVA/Typicals_83 - 'Titel' oslc_rm:satisfiedBy UST_AVA/Typicals_0009 - Vergabevertrag abschließen
- REQ_AVA/Typicals_84 - 'Titel' oslc_rm:satisfiedBy UST_AVA/Typicals_0002 - LV konfigurieren
- REQ_AVA/Typicals_84.1 - 'Titel' oslc_rm:satisfiedBy UST_AVA/Typicals_0002 - LV konfigurieren
- REQ_AVA/Typicals_84.2 - 'Titel' oslc_rm:satisfiedBy UST_AVA/Typicals_0002 - LV konfigurieren
- REQ_AVA/Typicals_84.3 - 'Titel' oslc_rm:satisfiedBy UST_AVA/Typicals_0002 - LV konfigurieren
- REQ_AVA/Typicals_84.4 - 'Titel' oslc_rm:satisfiedBy UST_AVA/Typicals_0002 - LV konfigurieren
- REQ_AVA/Typicals_84.5 - 'Titel' oslc_rm:satisfiedBy UST_AVA/Typicals_0002 - LV konfigurieren
- REQ_AVA/Typicals_84.6 - 'Titel' oslc_rm:satisfiedBy UST_AVA/Typicals_0002 - LV konfigurieren
- REQ_AVA/Typicals_85 - 'Titel' oslc_rm:satisfiedBy UST_AVA/Typicals_0003 - Kostenzuordnung festlegen
- REQ_AVA/Typicals_85.2 - 'Titel' oslc_rm:satisfiedBy UST_AVA/Typicals_0003 - Kostenzuordnung festlegen
- REQ_AVA/Typicals_86 - 'Titel' oslc_rm:satisfiedBy UST_AVA/Typicals_0016 - Kosten/Leistungs-SOLL-IST-Abgleich durchführen
- REQ_AVA/Typicals_89 - 'Titel' oslc_rm:satisfiedBy UST_AVA/Typicals_0002 - LV konfigurieren
- REQ_AVA/Typicals_92 - 'Titel' oslc_rm:satisfiedBy UST_AVA/Typicals_0010 - Vertragsfirmen beauftragen
- REQ_AVA/Typicals_93 - 'Titel' oslc_rm:satisfiedBy UST_AVA/Typicals_0006 - Selektierte Informationen mit Dritten (Bietern) austauschen
- REQ_AVA/Typicals_93.1 - 'Titel' oslc_rm:satisfiedBy UST_AVA/Typicals_0008 - Vergabevertag vorbereiten
- REQ_AVA/Typicals_93.3 - 'Titel' oslc_rm:satisfiedBy UST_AVA/Typicals_0009 - Vergabevertrag abschließen
- REQ_AVA/Typicals_95 - 'Titel' oslc_rm:satisfiedBy UST_AVA/Typicals_0011 - IST-Leistungen durch Auftragnehmer erfassen
- REQ_AVA/Typicals_95.1 - 'Titel' oslc_rm:satisfiedBy UST_AVA/Typicals_0011 - IST-Leistungen durch Auftragnehmer erfassen
- REQ_AVA/Typicals_95.10 - 'Titel' oslc_rm:satisfiedBy UST_AVA/Typicals_0011 - IST-Leistungen durch Auftragnehmer erfassen
- REQ_AVA/Typicals_95.2 - 'Titel' oslc_rm:satisfiedBy UST_AVA/Typicals_0011 - IST-Leistungen durch Auftragnehmer erfassen
- REQ_AVA/Typicals_95.3 - 'Titel' oslc_rm:satisfiedBy UST_AVA/Typicals_0011 - IST-Leistungen durch Auftragnehmer erfassen
- REQ_AVA/Typicals_95.4 - 'Titel' oslc_rm:satisfiedBy UST_AVA/Typicals_0011 - IST-Leistungen durch Auftragnehmer erfassen
- REQ_AVA/Typicals_95.5 - 'Titel' oslc_rm:satisfiedBy UST_AVA/Typicals_0011 - IST-Leistungen durch Auftragnehmer erfassen
- REQ_AVA/Typicals_95.6 - 'Titel' oslc_rm:satisfiedBy UST_AVA/Typicals_0011 - IST-Leistungen durch Auftragnehmer erfassen
- REQ_AVA/Typicals_95.7 - 'Titel' oslc_rm:satisfiedBy UST_AVA/Typicals_0011 - IST-Leistungen durch Auftragnehmer erfassen
- REQ_AVA/Typicals_95.8 - 'Titel' oslc_rm:satisfiedBy UST_AVA/Typicals_0011 - IST-Leistungen durch Auftragnehmer erfassen
- REQ_AVA/Typicals_95.9 - 'Titel' oslc_rm:satisfiedBy UST_AVA/Typicals_0011 - IST-Leistungen durch Auftragnehmer erfassen
- REQ_AVA/Typicals_97a - 'Titel' oslc_rm:satisfiedBy UST_AVA/Typicals_0011 - IST-Leistungen durch Auftragnehmer erfassen
- REQ_AVA/Typicals_98 - 'Titel' oslc_rm:satisfiedBy UST_AVA/Typicals_0017 - Auswertkriterien festlegen
- Beantragung - Projektkalkulation (Kalkulationsmodell) IREB:refines 3:Projekt beantragen
- Beantragung - Projektkalkulation (Kalkulationsmodell) IREB:refines 3:Projekt beantragen
- Beantragung - Projektkalkulation (Kalkulationsmodell) IREB:refines 3:Projekt beantragen
- Beantragung - Projektkalkulation (Kalkulationsmodell) IREB:refines 3:Projekt beantragen
- Beantragung - Kaufmännische Einordnung IREB:refines 3:Projekt beantragen
- Beantragung - Kaufmännische Einordnung IREB:refines 3:Projekt beantragen
- Beantragung - Planzahlen / Kennzahlen verwenden IREB:refines 3:Projekt beantragen
- Beantragung - Planzahlen / Kennzahlen verwenden IREB:refines 3:Projekt beantragen
- Beantragung - Dokumentation Beantragung IREB:refines 3:Projekt beantragen
- Beantragung - Dokumentation Beantragung IREB:refines 3:Projekt beantragen
- Beantragung - Dokumentation Beantragung IREB:refines 3:Projekt beantragen
- Beantragung - Dokumentation Beantragung IREB:refines 3:Projekt beantragen
- Beantragung - Sonstige IREB:refines 3:Projekt beantragen
- Beantragung - Sonstige IREB:refines 3:Projekt beantragen
- Beantragung - Sonstige IREB:refines 3:Projekt beantragen
- Beantragung - Sonstige IREB:refines 3:Projekt beantragen
- Beantragung - Sonstige IREB:refines 3:Projekt beantragen
- Beantragung - Sonstige IREB:refines 3:Projekt beantragen
- Review - WiRe IREB:refines 9:Projekt reviewen
- Review - WiRe IREB:refines 9:Projekt reviewen
- Review - Ermittlung Wirtschaftlichkeit IREB:refines 9:Projekt reviewen
- Review - Abweichungsanalyse IREB:refines 9:Projekt reviewen
- Beantragung - Dokumentation Beantragung IREB:refines 3:Projekt beantragen
- Beantragung - Dokumentation Beantragung IREB:refines 3:Projekt beantragen
- Bewertung neuer Projekte (Finanzraten, Mengen auf BM/BMT/BMG, Varianten)_A IREB:refines 24:WiRe und RBAM berechnen
- Bewertung neuer Projekte (Finanzraten, Mengen auf BM/BMT/BMG, Varianten)_B IREB:refines 11:Technische Lösung erarbeiten / überarbeiten
- Zuschüsse in der WiRe berücksichtigen IREB:refines 29:Kennzahlen nachberechnen
- Risikoparameter für RBAM berücksichtigen IREB:refines 24:WiRe und RBAM berechnen
- Risikoparameter für RBAM berücksichtigen IREB:refines 29:Kennzahlen nachberechnen
- Risikoparameter für RBAM berücksichtigen IREB:refines 44:WiRe und RBAM überarbeiten
- Übersicht Projektplanung auswerten IREB:refines 1:Projekt initialisieren
- Übersicht Projektplanung auswerten IREB:refines 2:Projekt konzipieren
- Übersicht Projektplanung auswerten IREB:refines 3:Projekt beantragen
- Daten für Kapitalkostenantrag (KKA) auswerten IREB:refines 1:Projekt initialisieren
- Daten für Kapitalkostenantrag (KKA) auswerten IREB:refines 2:Projekt konzipieren
- Mittelfristplanung und KKA erstellen IREB:refines 2:Projekt konzipieren
- Auswertung steuerungsrelevanter Kennzahlen IREB:refines 3:Projekt beantragen
- Auswertung steuerungsrelevanter Kennzahlen IREB:refines 9:Projekt reviewen
- Daten der Feinplanung in WiRe berücksichtigen IREB:refines 24:WiRe und RBAM berechnen
- Daten der Feinplanung in WiRe berücksichtigen IREB:refines 29:Kennzahlen nachberechnen
- Daten der Feinplanung in WiRe berücksichtigen IREB:refines 44:WiRe und RBAM überarbeiten
- Daten aus dem Projektprogramm und unterjähriger Projekte in WiRe berücksichtigen IREB:refines 24:WiRe und RBAM berechnen
- Daten aus dem Projektprogramm und unterjähriger Projekte in WiRe berücksichtigen IREB:refines 29:Kennzahlen nachberechnen
- Daten aus dem Projektprogramm und unterjähriger Projekte in WiRe berücksichtigen IREB:refines 44:WiRe und RBAM überarbeiten
- Kaufmännische Kennzahlen entsprechend des Kalkulationsmodells bei Steuerung Asset eigener Produkte berücksichtigen IREB:refines 3:Projekt beantragen
- Kaufmännische Kennzahlen entsprechend des Kalkulationsmodells bei Steuerung Asset eigener Produkte berücksichtigen IREB:refines 9:Projekt reviewen
- Projektstatus für Abweichungsanalysen auswerten IREB:refines 9:Projekt reviewen
- Auswertungsmöglichkeit historischer Daten für Planung und Prognose IREB:refines 9:Projekt reviewen
- WiRe und Grobplanung in TWE integrieren IREB:refines 44:WiRe und RBAM überarbeiten
- REQ_PortfolioMgmt_1 - 'Titel' oslc_rm:satisfiedBy Bewertung neuer Projekte (Finanzraten, Mengen auf BM/BMT/BMG, Varianten)_A
- REQ_PortfolioMgmt_2 - 'Titel' oslc_rm:satisfiedBy Bewertung neuer Projekte (Finanzraten, Mengen auf BM/BMT/BMG, Varianten)_B
- REQ_PortfolioMgmt_3 - 'Titel' oslc_rm:satisfiedBy Auswertung steuerungsrelevanter Kennzahlen
- REQ_PortfolioMgmt_4 - 'Titel' oslc_rm:satisfiedBy Auswertung steuerungsrelevanter Kennzahlen
- REQ_PortfolioMgmt_5 - 'Titel' oslc_rm:satisfiedBy Auswertung steuerungsrelevanter Kennzahlen
- REQ_PortfolioMgmt_6 - 'Titel' oslc_rm:satisfiedBy Auswertung steuerungsrelevanter Kennzahlen
- REQ_PortfolioMgmt_7 - 'Titel' oslc_rm:satisfiedBy Auswertung steuerungsrelevanter Kennzahlen
- REQ_PortfolioMgmt_8 - 'Titel' oslc_rm:satisfiedBy Auswertung steuerungsrelevanter Kennzahlen
- REQ_PortfolioMgmt_9 - 'Titel' oslc_rm:satisfiedBy Zuschüsse in der WiRe berücksichtigen
- REQ_PortfolioMgmt_10 - 'Titel' oslc_rm:satisfiedBy Zuschüsse in der WiRe berücksichtigen
- REQ_PortfolioMgmt_11 - 'Titel' oslc_rm:satisfiedBy Risikoparameter für RBAM berücksichtigen
- REQ_PortfolioMgmt_12 - 'Titel' oslc_rm:satisfiedBy Übersicht Projektplanung auswerten
- REQ_PortfolioMgmt_13 - 'Titel' oslc_rm:satisfiedBy Übersicht Projektplanung auswerten
- REQ_PortfolioMgmt_14 - 'Titel' oslc_rm:satisfiedBy Daten für Kapitalkostenantrag (KKA) auswerten
- REQ_PortfolioMgmt_15 - 'Titel' oslc_rm:satisfiedBy Daten für Kapitalkostenantrag (KKA) auswerten
- REQ_PortfolioMgmt_16 - 'Titel' oslc_rm:satisfiedBy Daten für Kapitalkostenantrag (KKA) auswerten
- REQ_PortfolioMgmt_17 - 'Titel' oslc_rm:satisfiedBy Daten für Kapitalkostenantrag (KKA) auswerten
- REQ_PortfolioMgmt_18 - 'Titel' oslc_rm:satisfiedBy Daten für Kapitalkostenantrag (KKA) auswerten
- REQ_PortfolioMgmt_19 - 'Titel' oslc_rm:satisfiedBy Daten für Kapitalkostenantrag (KKA) auswerten
- REQ_PortfolioMgmt_20 - 'Titel' oslc_rm:satisfiedBy Mittelfristplanung und KKA erstellen
- REQ_PortfolioMgmt_21 - 'Titel' oslc_rm:satisfiedBy Mittelfristplanung und KKA erstellen
- REQ_PortfolioMgmt_22 - 'Titel' oslc_rm:satisfiedBy Mittelfristplanung und KKA erstellen
- REQ_PortfolioMgmt_23 - 'Titel' oslc_rm:satisfiedBy Daten der Feinplanung in WiRe berücksichtigen
- REQ_PortfolioMgmt_24 - 'Titel' oslc_rm:satisfiedBy Daten der Feinplanung in WiRe berücksichtigen
- REQ_PortfolioMgmt_25 - 'Titel' oslc_rm:satisfiedBy Daten aus dem Projektprogramm und unterjähriger Projekte in WiRe berücksichtigen
- REQ_PortfolioMgmt_26 - 'Titel' oslc_rm:satisfiedBy Daten aus dem Projektprogramm und unterjähriger Projekte in WiRe berücksichtigen
- REQ_PortfolioMgmt_27 - 'Titel' oslc_rm:satisfiedBy Kaufmännische Kennzahlen entsprechend des Kalkulationsmodells bei Steuerung Asset eigener Produkte berücksichtigen
- REQ_PortfolioMgmt_28 - 'Titel' oslc_rm:satisfiedBy Kaufmännische Kennzahlen entsprechend des Kalkulationsmodells bei Steuerung Asset eigener Produkte berücksichtigen
- REQ_PortfolioMgmt_29 - 'Titel' oslc_rm:satisfiedBy Kaufmännische Kennzahlen entsprechend des Kalkulationsmodells bei Steuerung Asset eigener Produkte berücksichtigen
- REQ_PortfolioMgmt_30 - 'Titel' oslc_rm:satisfiedBy Kaufmännische Kennzahlen entsprechend des Kalkulationsmodells bei Steuerung Asset eigener Produkte berücksichtigen
- REQ_PortfolioMgmt_31 - 'Titel' oslc_rm:satisfiedBy Kaufmännische Kennzahlen entsprechend des Kalkulationsmodells bei Steuerung Asset eigener Produkte berücksichtigen
- REQ_PortfolioMgmt_32 - 'Titel' oslc_rm:satisfiedBy Kaufmännische Kennzahlen entsprechend des Kalkulationsmodells bei Steuerung Asset eigener Produkte berücksichtigen
- REQ_PortfolioMgmt_33 - 'Titel' oslc_rm:satisfiedBy Projektstatus für Abweichungsanalysen auswerten
- REQ_PortfolioMgmt_34 - 'Titel' oslc_rm:satisfiedBy Auswertungsmöglichkeit historischer Daten für Planung und Prognose
- REQ_PortfolioMgmt_35 - 'Titel' oslc_rm:satisfiedBy Auswertungsmöglichkeit historischer Daten für Planung und Prognose
- REQ_PortfolioMgmt_36- 'Titel' oslc_rm:satisfiedBy Auswertungsmöglichkeit historischer Daten für Planung und Prognose
- REQ_PortfolioMgmt_37 - 'Titel' oslc_rm:satisfiedBy Auswertungsmöglichkeit historischer Daten für Planung und Prognose
- REQ_PortfolioMgmt_38 - 'Titel' oslc_rm:satisfiedBy WiRe und Grobplanung in TWE integrieren
- REQ_PortfolioMgmt_39 - 'Titel' oslc_rm:satisfiedBy WiRe und Grobplanung in TWE integrieren
- REQ_PortfolioMgmt_40 - 'Titel' oslc_rm:satisfiedBy WiRe und Grobplanung in TWE integrieren
- REQ_PortfolioMgmt_41 - 'Titel' oslc_rm:satisfiedBy Projektstatus einsehen
- REQ_PortfolioMgmt_42 - 'Titel' oslc_rm:satisfiedBy Projektstatus einsehen
