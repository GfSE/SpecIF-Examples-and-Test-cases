# A resource with properties covering all dataTypes - adopt-1
Excerpt from example 'Dimmer'.
- Rights: Creative Commons 4.0 CC BY-SA, https://creativecommons.org/licenses/by-sa/4.0/

## Requirements (SpecIF:Heading)

## Dim an electric load (IREB:Requirement)
- dcterms:identifier: REQ_014
- dcterms:description: The user can set the intensity level of an electric load such as a light [[bulb]]. Pressing a button 'up' or 'down', the intensity is increased or decreased following a quasi-stepless ramp.
- SpecIF:Status: 20_drafted
- Discipline: Mechanics, Software

## Switch an electric load (IREB:Requirement)
- dcterms:identifier: REQ_016
- dcterms:description: The user can immediately switch 'on' or 'off' the electric load. The intensity set to the maximum resp. minimum level, as defined by installation parameters.
- SpecIF:Status: 40_approved
- SpecIF:Priority: SpecIF:priorityMedium
- SpecIF:Perspective: User
- Discipline: Electronics, Software
