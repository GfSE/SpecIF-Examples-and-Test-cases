# A test with formatted text containing line-breaks
- Rights: Creative Commons 4.0 CC BY-SA, https://creativecommons.org/licenses/by-sa/4.0/

## A test with formatted text containing line-breaks (SpecIF:Hierarchy)

## Text with a simple markup-table with line-break in a cell (SpecIF:Paragraph)
- dcterms:description: Text before table - **bold** and *italic* style. | Name | Comment | Telephone | | --- | --- | --- | | Oskar Surname | Lorem ipsum dolor sit amet,
  consetetur sadipscing elitr | | Text after table - **bold** and *italic* style.

## Text with a simple XHTML-table with line-break in a cell (SpecIF:Paragraph)
- dcterms:description:
  | Name | Comment | Telephone |
  | --- | --- | --- |
  | Oskar Surname | Lorem ipsum dolor sit amet, consetetur sadipscing elitr |  |

## Text with multiple paragraphs (SpecIF:Paragraph)
- dcterms:title: Text with multiple paragraphs and line-break
- dcterms:description: First paragraph, an empty paragraph follows:
  Nächster Absatz.
  Lorem ipsum dolor sit amet,
  consetetur sadipscing elitr, sed diam nonumy eirmod tempor invidunt ut labore et dolore magna aliquyam erat, sed diam voluptua. At vero eos et accusam et justo duo dolores et ea rebum. Stet clita kasd gubergren, no sea takimata sanctus est Lorem ipsum dolor sit amet. Lorem ipsum dolor sit amet, consetetur sadipscing elitr, sed diam nonumy eirmod tempor invidunt ut labore et dolore magna aliquyam erat, sed diam voluptua. At vero eos et accusam et justo duo dolores et ea rebum. Stet clita kasd gubergren,
  no sea takimata sanctus est Lorem ipsum dolor sit amet.
  A hyperlink without <a> tag: https://specif.de/apps/edit#import=../examples/Dimmer.specifz
  Dernier paragraphe.
