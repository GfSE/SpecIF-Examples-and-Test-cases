# Project 'Related Terms'
- Rights: Creative Commons 4.0 CC BY-SA, https://creativecommons.org/licenses/by-sa/4.0/

## Vehicle (SpecIF:NameResourceClass)

## Lorry (SpecIF:NameResourceClass)

## Statements
- Lorry SysML:isSpecializationOf Vehicle
