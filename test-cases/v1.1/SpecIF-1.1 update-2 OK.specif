# SpecIF-0.10.2 update-2 OK
all is fine; resource 'cable' has been added.
- Rights: Creative Commons 4.0 CC BY-SA, https://creativecommons.org/licenses/by-sa/4.0/

## SpecIF-0.10.2 update-2 OK (SpecIF:Outline)
- dcterms:description: all is fine; resource 'cable' has been added.

## System Composition (SpecIF:Heading)
- dcterms:description: .. showing the system and its composition of modules (at a higher level) and components (at a lower level). The relevant interfaces between the disciplines mechanical, electrical and software engineering are shown.

## SmartHome System (SpecIF:View)
- dcterms:description: The Smart-Home-System consists of sensors on the left side, the controller in the middle and the actuators on the right side.
  Model View:
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- SpecIF:Notation: FMC Block Diagram
- SpecIF:TermStatus: SpecIF:LifecycleStatusInitial

## Scenarios (SpecIF:Heading)
- dcterms:description: .. showing the behavioral aspects of system design, both from external user perspective ('black box') and from internal perspective ('white box').

## Dimming (SpecIF:Heading)

## User Activity (SpecIF:View)
- dcterms:description: This shows the defined sequences of manual operation to activate the device.
  Model View:
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- SpecIF:Notation: BPMN Process Model
- SpecIF:TermStatus: SpecIF:LifecycleStatusDrafted

## Parts List (SpecIF:Heading)
- dcterms:description: This Parts List has been automatically generated from the model.

## Bulb (FMC:Actor)
- dcterms:description: Dimmable candescent light-bulb 230V. (Rev.241)

## Cable (FMC:Actor)
- dcterms:description: A cable with 3-wires.

## down (FMC:State)
- dcterms:description: The button to drive down the dimmer, shading or similar devices.

## Model Elements (Glossary) (SpecIF:Heading)
- dcterms:type: SpecIF:Glossary

## Actors (SpecIF:Heading)
- dcterms:description: An 'Actor' is a fundamental model element type representing an active entity, be it an activity, a process step, a function, a system component or a role.
  The particular use of FMC:Actor is specified with a [[dcterms:type]] property. The values of that property can be ontology-terms, such as [[bpmn:timer]].
- dcterms:type: SpecIF:Heading

## States (SpecIF:Heading)
- dcterms:description: A 'State' is a fundamental model element type representing a passive entity, be it a value, a condition, an information storage or even a physical shape.
- dcterms:type: SpecIF:Heading

## Events (SpecIF:Heading)
- dcterms:description: An 'Event' is a fundamental model element type representing a time reference, a change in condition/value or more generally a synchronization primitive.
- dcterms:type: SpecIF:Heading

## Collections and Groups (SpecIF:Heading)
- dcterms:description: A 'Collection' is a logic (often conceptual) group of resources linked with a [[SpecIF:contains]] statement. It corresponds to a 'Group' in BPMN Diagrams.
  BPMN: An arbitrary set of objects can be defined as a Group to show that they logically belong together. (source: BPMN Tutorial)
- dcterms:type: SpecIF:Heading

## Statements
- SmartHome System SpecIF:shows Bulb
- SmartHome System SpecIF:shows down
