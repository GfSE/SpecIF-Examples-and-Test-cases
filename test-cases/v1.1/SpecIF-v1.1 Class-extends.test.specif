# A test with good 'extends', i.e. type specialisations
- Rights: Creative Commons 4.0 CC BY-SA, https://creativecommons.org/licenses/by-sa/4.0/

## Title 1 (SpecIF:Paragraph)
- dcterms:description: A test with good 'extends', i.e. type specialisations

## Title 2 (SpecIF:Paragraph)
- dcterms:description: Formatted Text

## Title 3 (SpecIF:Paragraph)
- dcterms:description: This element has an extended property
- SpecIF:Priority: Medium
