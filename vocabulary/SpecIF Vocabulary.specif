# SpecIF Vocabulary
The SpecIF Vocabulary (or Glossary) collects terms used in the domain of systems engineering and requirements management. Agreed-upon terms help both collaborators to communicate more clearly and systems to match data fields automatically.
- Rights: Creative Commons 4.0 CC BY-SA, https://creativecommons.org/licenses/by-sa/4.0/

## Introduction (SpecIF:Heading)
- dcterms:description: The SpecIF Vocabulary (or Glossary) collects terms used in the domain of systems engineering and requirements management. Agreed-upon terms help both collaborators to communicate more clearly and systems to match data fields automatically. SpecIF adopts terms and their definitions from other initiatives, for example from the Dublin Core Metadata Initiative (DCMI), the Open Services for Lifecycle Collaboration (OSLC) and the International Requirements Engineering Board (IREB). The ProSTEP iViP association has also defined a set of attribute names to be used in ReqIF data, but those are not freely available and cannot be referenced here.
  All terms carry a namespace, which is the first part separated with ':' or '.' ― they are thus easily recognized in text and data fields. For display, systems may choose to replace SpecIF terms by domain or language specific words. This collection itself is structured according to SpecIF using it's vocabulary. Hence, the titles are recognized as such, because they are tagged with "[[dcterms:title]]", whereas paragraphs like this one are tagged with "[[dcterms:description]]".
  The terms have a lifecycle status as follows:
  - experimental: The term is being used in first projects, but has not yet any normative maturity.
  - submitted: The term has been submitted for adoption.
  - preferred: The term has been adopted for use with SpecIF and is preferred among equivalent terms.
  - equivalent: The term has been adopted for use with SpecIF, but another equivalent term is preferred.
  - deprecated: The term shall not any more be used with SpecIF; use an equivalent term.
  The Specification Interchange Facility (SpecIF) is the result of an initiative by the Gesellschaft für Systems Engineering (GfSE), the German chapter of The International Council on Systems Engineering (INCOSE).
  All information provided here is made available according to Creative Commons 4.0 CC BY-SA or the license chosen by the respective publishers. We appreciate any contribution or proposal; please contact Dr. Oskar von Dungern from adesso SE.
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
## Resource Class Names (SpecIF:Heading)
- dcterms:description: A resource represents an artefact, e.g. a model element or a requirement. The terms listed in this chapter may be used to distinguish different classes (types) of artefacts constituting a system specification. A resource may serve as subject or as object in a subject-predicate-object statement. Each resource class may define an individual set of properties for carrying the information 'payload'.
  A resource class corresponds to a 'SPEC-OBJECT-TYPE' and a resource is a 'SPEC-OBJECT' in the Requirements Interchange Format (ReqIF). In ArchiMate® 3.0, a resource is an Element.

## Statement Class Names (SpecIF:Heading)
- dcterms:description: A statement represents a logic affinity or association between two resources, i.e. system specification artefacts. The terms listed in this chapter may be used as predicates to distinguish different classes (types) of statements. Each statement class may define an individual set of properties for carrying the information 'payload'.
  In SpecIF, a statement is first order predicate logic. For each predicate (statement class), a list of eligible resource classes may be defined for subjects and objects, respectively. For example, the predicate [[oslc_rm:satisfies]] is usually confined to [[FMC:Actor]] and [[FMC:State]] as subject and [[IREB:Requirement]] as object.
  A statement consisting of subject-predicate-object (where a resource may serve as subject or object) can be directly mapped to a ReqIF relation, a RDF triple in OSLC or 'linked data' in general.
  A statement class corresponds to a 'SPEC-RELATION-TYPE' and a statement is a 'SPEC-RELATION' in the Requirements Interchange Format (ReqIF). In ArchiMate® 3.0, a statement is a Relationship.

## Property Names (SpecIF:Heading)
- dcterms:description: A property carries information 'payload' and may be applied to resources or statements. The SpecIF terms listed in this chapter are used as property name/title, whereas the information is provided as 'value'. Usually a combination of complimentary properties is used per resource or statement class.
  A property corresponds to an 'ATTRIBUTE-DEFINITION' resp. 'ATTRIBUTE-VALUE' in the Requirements Interchange Format (ReqIF).

## Property Values (SpecIF:Heading)
- dcterms:description: These are terms for certain enumerated property values. Not only the property titles, but also any enumerated value must be mapped between different systems or domains; therefore using defined terms is beneficial. Of course, like any other vocabulary term, any term used as property value for transmission or storage can be translated for display.
  This is still experimental. Please let us know what you think: Dr. Oskar von Dungern from adesso SE.

## SpecIF:Heading (Resource-Term)
- dcterms:description: A 'Heading' is a chapter title at any level.
- SpecIF:Origin: http://specif.de
- SpecIF:Status: preferred

## SpecIF:Paragraph (Resource-Term)
- dcterms:description: A 'Paragraph' is an unspecified information in a document at any level.
- SpecIF:Origin: http://specif.de
- SpecIF:Status: preferred

## SpecIF:Diagram (Resource-Term)
- dcterms:description: A 'Diagram' is a graphical model view with a specific communication purpose, e.g. a business process or system composition.
- SpecIF:Origin: http://specif.de
- SpecIF:Status: preferred

## SpecIF:View (Resource-Term)
- dcterms:description: A 'View' is a graphical model view with a specific communication purpose, e.g. a business process or system composition.
- SpecIF:Origin: http://specif.de
- SpecIF:Status: deprecated

## FMC:Plan (Resource-Term)
- dcterms:description: A 'Plan' is a graphical model view with a specific communication purpose, e.g. a business process or system composition.
- SpecIF:Origin: http://fmc-modeling.org/
- SpecIF:Status: equivalent

## FMC:Actor (Resource-Term)
- dcterms:description: An 'Actor' is a fundamental model element type representing an active entity, be it an activity, a process step, a function, a system component or a role.
  It is advised to specify the particular use of FMC:Actor with a [[dcterms:type]] property. The values of that property can be defined terms, such as [[BPMN:Timer]].
- SpecIF:Origin: http://fmc-modeling.org/
- SpecIF:Status: preferred

## FMC:State (Resource-Term)
- dcterms:description: A 'State' is a fundamental model element type representing a passive entity, be it a value, a condition, an information storage or even a physical shape.
- SpecIF:Origin: http://fmc-modeling.org/
- SpecIF:Status: preferred

## FMC:Event (Resource-Term)
- dcterms:description: An 'Event' is a fundamental model element type representing a time reference, a change in condition/value or more generally a synchronisation primitive.
- SpecIF:Origin: http://fmc-modeling.org/
- SpecIF:Status: preferred

## IREB:Requirement (Resource-Term)
- dcterms:description: A 'Requirement' is a singular documented physical and functional need that a particular design, product or process must be able to perform. (source: Wikipedia)
  Definition (source: IREB):
  1. A condition or capability needed by a user to solve a problem or achieve an objective.
  2. A condition or capability that must be met or possessed by a system or system component to satisfy a contract, standard, specification, or other formally imposed documents.
  3. A documented representation of a condition or capability as in (1) or (2).
  Note: The definition above is the classic one from IEEE Std 610.12 of 1990. Alternatively, we also give a more modern definition:
  1. A need perceived by a stakeholder.
  2. A capability or property that a system shall have.
  3. A documented representation of a need, capability or property.
- SpecIF:Origin: https://www.ireb.org/content/downloads/1-cpre-glossary/ireb_cpre_glossary_17.pdf
- SpecIF:Status: preferred

## SpecIF:Feature (Resource-Term)
- dcterms:description: A 'Feature' is an intentional distinguishing characteristic of a system, often a unique selling proposition.
- SpecIF:Origin: http://specif.de
- SpecIF:Status: preferred

## SpecIF:Comment (Resource-Term)
- dcterms:description: A 'Comment' is reader feedback referring to any resource.
- SpecIF:Origin: http://specif.de
- SpecIF:Status: preferred

## SpecIF:Collection (Resource-Term)
- dcterms:description: A 'Collection' is an arbitrary group of resources linked with a [[SpecIF:contains]] statement. It corresponds to a 'Group' in BPMN Diagrams.
  BPMN: An arbitrary set of objects can be defined as a Group to show that they logically belong together. (source: BPMN Tool)
- SpecIF:Origin: http://specif.de
- SpecIF:Status: experimental

## BPMN:Group (Resource-Term)
- dcterms:description: A 'Group' is an arbitrary group of resources linked with a [[SpecIF:contains]] statement.
  BPMN: An arbitrary set of objects can be defined as a Group to show that they logically belong together. (source: BPMN Tool)
- SpecIF:Origin: http://specif.de
- SpecIF:Status: experimental

## SpecIF:Note (Resource-Term)
- dcterms:description: A 'Note' is additional information by the author referring to any resource.
- SpecIF:Origin: http://specif.de
- SpecIF:Status: preferred

## SpecIF:Issue (Resource-Term)
- dcterms:description: An 'Issue' is a question to answer or decision to take which is worth tracking.
- SpecIF:Origin: http://specif.de
- SpecIF:Status: preferred

## IREB:Risk (Resource-Term)
- dcterms:description: An event that threatens the success of an endeavor, e.g., of developing or operating a system. A risk is typically assessed in terms of its probability and potential damage. (source: IREB)
- SpecIF:Origin: https://www.ireb.org/content/downloads/1-cpre-glossary/ireb_cpre_glossary_17.pdf
- SpecIF:Status: preferred

## foaf:Person (Resource-Term)
- dcterms:description: The Person class represents people. Something is a Person if it is a person. We don't nitpic about whether they're alive, dead, real, or imaginary. (source: FOAF)
- SpecIF:Origin: http://xmlns.com/foaf/
- SpecIF:Status: preferred

## SpecIF:shows (Predicate-Term)
- dcterms:description: A [[SpecIF:Diagram]] 'shows' a model element, e.g, a [[FMC:Actor]], [[FMC:State]] or [[FMC:Event]].
- SpecIF:Origin: http://specif.de
- SpecIF:Status: preferred

## SpecIF:contains (Predicate-Term)
- dcterms:description: A [[FMC:Actor]] or [[FMC:State]] 'contains' a [[FMC:Actor]], [[FMC:State]] or [[FMC:Event]]. More concretely, Component-A contains Component-B.
- SpecIF:Origin: http://specif.de
- SpecIF:Status: preferred

## oslc_rm:satisfies (Predicate-Term)
- dcterms:description: The object is satisfied by the subject. (source: OSLC)
  SpecIF suggests that the subject is confined to a model element, e.g, a [[FMC:Actor]] or [[FMC:State]], and the object is confined to a [[IREB:Requirement]]. More concretely, an example for this type of statement is 'Component-X satisfies 'Requirement-4711'.
- SpecIF:Origin: http://open-services.net/bin/view/Main/RmSpecificationV2
- SpecIF:Status: preferred

## oslc_rm:satisfiedBy (Predicate-Term)
- dcterms:description: The subject is satisfied by the object. For example, a user requirement is satisfied by a system requirement. (source: OSLC)
- SpecIF:Origin: http://open-services.net/bin/view/Main/RmSpecificationV2

## SpecIF:satisfies (Predicate-Term)
- dcterms:description: A [[FMC:Actor]] or [[FMC:State]] 'satisfies' a [[IREB:Requirement]].
- SpecIF:Origin: http://specif.de
- SpecIF:Status: equivalent

## SpecIF:implements (Predicate-Term)
- dcterms:description: A [[FMC:Actor]] or [[FMC:State]] 'implements' a [[SpecIF:Feature]].
- SpecIF:Origin: http://specif.de
- SpecIF:Status: preferred

## SpecIF:reads (Predicate-Term)
- dcterms:description: A [[FMC:Actor]] 'reads' a [[FMC:State]].
- SpecIF:Origin: http://specif.de
- SpecIF:Status: preferred

## SpecIF:writes (Predicate-Term)
- dcterms:description: A [[FMC:Actor]] 'writes' (changes) a [[FMC:State]].
- SpecIF:Origin: http://specif.de
- SpecIF:Status: preferred

## SpecIF:stores (Predicate-Term)
- dcterms:description: A [[FMC:Actor]] 'stores' (writes and reads) a [[FMC:State]].
- SpecIF:Origin: http://specif.de
- SpecIF:Status: preferred

## SpecIF:follows (Predicate-Term)
- dcterms:description: A [[FMC:Actor]] 'follows' a [[FMC:Actor]]; e.g. in a business process or activity flow.
- SpecIF:Origin: http://specif.de
- SpecIF:Status: preferred

## SpecIF:precedes (Predicate-Term)
- dcterms:description: A [[FMC:Actor]] 'precedes' a [[FMC:Actor]]; e.g. in a business process or activity flow.
- SpecIF:Origin: http://specif.de
- SpecIF:Status: experimental

## SpecIF:signals (Predicate-Term)
- dcterms:description: A [[FMC:Actor]] 'signals' a [[FMC:Event]].
- SpecIF:Origin: http://specif.de
- SpecIF:Status: preferred

## SpecIF:triggers (Predicate-Term)
- dcterms:description: A [[FMC:Event]] 'triggers' a [[FMC:Actor]].
- SpecIF:Origin: http://specif.de
- SpecIF:Status: preferred

## SpecIF:dependsOn (Predicate-Term)
- dcterms:description: A [[IREB:Requirement]] 'depends on' another [[IREB:Requirement]].
- SpecIF:Origin: http://specif.de
- SpecIF:Status: preferred

## SysML:traces (Predicate-Term)
- dcterms:description: A [[IREB:Requirement]] traces another [[IREB:Requirement]].
- SpecIF:Origin: http://specif.de
- SpecIF:Status: preferred

## SysML:isDerivedFrom (Predicate-Term)
- dcterms:description: A [[IREB:Requirement]] isDerivedFrom another [[IREB:Requirement]].
- SpecIF:Origin: http://specif.de
- SpecIF:Status: preferred

## IREB:refines (Predicate-Term)
- dcterms:description: A [[IREB:Requirement]] refines another [[IREB:Requirement]].
- SpecIF:Origin: http://specif.de
- SpecIF:Status: preferred

## SpecIF:duplicates (Predicate-Term)
- dcterms:description: A [[IREB:Requirement]] 'duplicates' another [[IREB:Requirement]].
- SpecIF:Origin: http://specif.de
- SpecIF:Status: preferred

## SpecIF:contradicts (Predicate-Term)
- dcterms:description: A [[IREB:Requirement]] 'contradicts' another [[IREB:Requirement]].
- SpecIF:Origin: http://specif.de
- SpecIF:Status: preferred

## SysML:isAllocatedTo (Predicate-Term)
- dcterms:description: An [[FMC:Actor]] is allocated to another [[FMC:Actor]] (e.g. a logical function is allocated to a physical component.
- SpecIF:Origin: http://specif.de
- SpecIF:Status: preferred

## SpecIF:isAssociatedWith (Predicate-Term)
- dcterms:description: A [[FMC:State]] is associated with another [[FMC:State]] (e.g. a class is associated with another class, as shown in a UML Class Diagram).
- SpecIF:Origin: http://specif.de
- SpecIF:Status: preferred

## SysML:isComposedOf (Predicate-Term)
- dcterms:description: An [[FMC:Actor]] is composed of another [[FMC:Actor]].
- SpecIF:Origin: http://specif.de
- SpecIF:Status: preferred

## SysML:isAggregatedBy (Predicate-Term)
- dcterms:description: An [[FMC:Actor]] is aggregated by another [[FMC:Actor]].
- SpecIF:Origin: http://specif.de
- SpecIF:Status: preferred

## SysML:uses (Predicate-Term)
- SpecIF:Origin: http://specif.de
- SpecIF:Status: preferred

## SysML:extends (Predicate-Term)
- dcterms:description: An [[FMC:Actor]] <> extends another [[FMC:Actor]] <>.
- SpecIF:Origin: http://specif.de
- SpecIF:Status: preferred

## SysML:includes (Predicate-Term)
- dcterms:description: An [[FMC:Actor]] <> includes another [[FMC:Actor]] <>.
- SpecIF:Origin: http://specif.de
- SpecIF:Status: preferred

## SysML:isGeneralisationOf (Predicate-Term)
- dcterms:description: An [[FMC:Actor]] is is generalisation of another [[FMC:Actor]]; similarly for [[FMC:State]] and [[FMC:Event]].
- SpecIF:Origin: http://specif.de
- SpecIF:Status: preferred

## SysML:isSpecialisationOf (Predicate-Term)
- dcterms:description: An [[FMC:Actor]] is is specialisation of another [[FMC:Actor]]; similarly for [[FMC:State]] and [[FMC:Event]].
- SpecIF:Origin: http://specif.de
- SpecIF:Status: preferred

## SpecIF:inheritsFrom (Predicate-Term)
- dcterms:description: A [[FMC:State]] inherits from another [[FMC:State]] (e.g. a class inherits from another class, as shown in a UML Class Diagram).
- SpecIF:Origin: http://specif.de
- SpecIF:Status: equivalent

## SpecIF:actorInheritsFrom (Predicate-Term)
- dcterms:description: A [[FMC:Actor]] inherits from another [[FMC:Actor]].
- SpecIF:Origin: http://specif.de
- SpecIF:Status: preferred

## SpecIF:stateInheritsFrom (Predicate-Term)
- dcterms:description: A [[FMC:State]] inherits from another [[FMC:State]] (e.g. a class inherits from another class, as shown in a UML Class Diagram).
- SpecIF:Origin: http://specif.de
- SpecIF:Status: preferred

## SpecIF:eventInheritsFrom (Predicate-Term)
- dcterms:description: A [[FMC:Event]] inherits from another [[FMC:Event]].
- SpecIF:Origin: http://specif.de
- SpecIF:Status: preferred

## SpecIF:refersTo (Predicate-Term)
- dcterms:description: A [[SpecIF:Comment]], [[SpecIF:Note]] or [[SpecIF:Issue]] 'refers to' any other resource.
- SpecIF:Origin: http://specif.de
- SpecIF:Status: preferred

## SpecIF:commentRefersTo (Predicate-Term)
- dcterms:description: A [[SpecIF:Comment]] 'refers to' any other resource.
- SpecIF:Origin: http://specif.de
- SpecIF:Status: preferred

## SpecIF:mentions (Predicate-Term)
- dcterms:description: A resource's text refers to another resorce (e.g. by hyper-link).
- SpecIF:Origin: http://specif.de
- SpecIF:Status: preferred

## SpecIF:isSynonymOf (Predicate-Term)
- dcterms:description: A term is synonymous with another term, if both represent the same concept.
  According to Wikipedia, "a synonym is a word or phrase that means exactly or nearly the same as another word or phrase in the same language. Words that are synonyms are said to be synonymous".
- SpecIF:Origin: http://specif.de
- SpecIF:Status: preferred

## SpecIF:isInverseOf (Predicate-Term)
- dcterms:description: A term is the inverse of another term.
  For example, a system 'B' contains a component '11', thus '11' isContainedBy 'B'.
- SpecIF:Origin: http://specif.de
- SpecIF:Status: experimental

## owl:sameAs (Predicate-Term)
- dcterms:description: An owl:sameAs statement indicates that two URI references actually refer to the same thing: the individuals have the same "identity". (source: OWL)
- SpecIF:Origin: https://www.w3.org/TR/owl-ref
- SpecIF:Status: preferred

## SpecIF:sameAs (Predicate-Term)
- dcterms:description: A resource represents the same entity as another resource.
- SpecIF:Origin: http://specif.de
- SpecIF:Status: equivalent

## SpecIF:Hierarchy (Resource-Term)
- dcterms:description: A root of a document structure with references to resources.
- SpecIF:Origin: http://specif.de
- SpecIF:Status: preferred

## SpecIF:Outline (Resource-Term)
- dcterms:description: A root of a document structure with references to resources.
- SpecIF:Origin: http://specif.de
- SpecIF:Status: equivalent

## SpecIF:BillOfMaterials (Resource-Term)
- dcterms:description: A bill of materials or product structure (sometimes bill of material, BOM or associated list) is a list of the raw materials, sub-assemblies, intermediate assemblies, sub-components, parts and the quantities of each needed to manufacture an end product. A BOM may be used for communication between manufacturing partners, or confined to a single manufacturing plant. (source: Wikipedia)
- SpecIF:Origin: http://specif.de
- SpecIF:Status: preferred

## dcterms:title (Property-Term)
- dcterms:description: A name given to the resource. (source: DCMI)
  Title (reference: Dublin Core) of the resource represented as rich text in XHTML content. SHOULD include only content that is valid inside an XHTML <span> element. (source: OSLC)
- SpecIF:Origin: http://dublincore.org/specifications/
- SpecIF:Status: preferred

## dcterms:description (Property-Term)
- dcterms:description: An account of the resource. (source: DCMI)
  Descriptive text (reference: Dublin Core) about resource represented as rich text in XHTML content. SHOULD include only content that is valid and suitable inside an XHTML <div> element. (source: OSLC)
- SpecIF:Origin: http://dublincore.org/specifications/
- SpecIF:Status: preferred

## dcterms:identifier (Property-Term)
- dcterms:description: A unique reference to the resource within a given context. (source: DCMI)
  An identifier for a resource. This identifier may be unique with a scope that is defined by the RM provider. Assigned by the service provider when a resource is created. Not intended for end-user display. (source: OSLC)
- SpecIF:Origin: http://dublincore.org/specifications/
- SpecIF:Status: preferred

## SpecIF:Id (Property-Term)
- dcterms:description: A unique reference to the resource within a given context.
- SpecIF:Origin: http://specif.de
- SpecIF:Status: deprecated

## dcterms:subject (Property-Term)
- dcterms:description: The topic of the resource. (source: DCMI)
  Tag or keyword for a resource. Each occurrence of a dcterms:subject property denotes an additional tag for the resource. (source: OSLC)
- SpecIF:Origin: http://dublincore.org/specifications/
- SpecIF:Status: preferred

## dcterms:creator (Property-Term)
- dcterms:description: An entity primarily responsible for making the resource. (source: DCMI)
  Creator(s) of resource (reference: Dublin Core). It is likely that the target resource will be a [[foaf:Person]] but that is not necessarily the case. (source: OSLC)
- SpecIF:Origin: http://dublincore.org/specifications/
- SpecIF:Status: equivalent

## SpecIF:createdBy (Property-Term)
- dcterms:description: A resource primarily responsible for making the resource.
- SpecIF:Origin: http://specif.de
- SpecIF:Status: preferred

## dcterms:created (Property-Term)
- dcterms:description: Timestamp of resource creation. (source: DCMI)
- SpecIF:Origin: http://dublincore.org/specifications/
- SpecIF:Status: equivalent

## SpecIF:createdAt (Property-Term)
- dcterms:description: Date/time of creation of the resource.
- SpecIF:Origin: http://specif.de
- SpecIF:Status: preferred

## SpecIF:changedBy (Property-Term)
- dcterms:description: The author who made the last modification.
- SpecIF:Origin: http://specif.de
- SpecIF:Status: preferred

## dcterms:modified (Property-Term)
- dcterms:description: Timestamp last latest resource modification. (source: DCMI)
- SpecIF:Origin: http://dublincore.org/specifications/
- SpecIF:Status: equivalent

## SpecIF:changedAt (Property-Term)
- dcterms:description: Date/time on which the resource was changed last.
- SpecIF:Origin: http://specif.de
- SpecIF:Status: preferred

## dcterms:contributor (Property-Term)
- dcterms:description: A resource responsible for making contributions to the resource. (source: DCMI)
- SpecIF:Origin: http://dublincore.org/specifications/
- SpecIF:Status: preferred

## dcterms:rightsHolder (Property-Term)
- dcterms:description: A person or organization owning or managing rights over the resource. (source: DCMI)
- SpecIF:Origin: http://dublincore.org/specifications/
- SpecIF:Status: preferred

## dcterms:rights (Property-Term)
- dcterms:description: Information about rights held in and over the resource. (source: DCMI)
- SpecIF:Origin: http://dublincore.org/specifications/
- SpecIF:Status: preferred

## rdf:type (Property-Term)
- dcterms:description: rdf:type is an instance of rdf:Property that is used to state that a resource is an instance of a class.
  A triple of the form: R rdf:type C states that C is an instance of rdfs:Class and R is an instance of C.
  The rdfs:domain of rdf:type is rdfs:Resource. The rdfs:range of rdf:type is rdfs:Class.
- SpecIF:Origin: https://www.w3.org/TR/rdf-schema/#ch_type
- SpecIF:Status: preferred

## oslc:shortTitle (Property-Term)
- dcterms:description: Short name identifying a resource, often used as an abbreviated identifier for presentation to end-users. SHOULD include only content that is valid inside an XHTML <span> element.
- SpecIF:Origin: http://open-services.net/bin/view/Main/RmSpecificationV2

## oslc:serviceProvider (Property-Term)
- dcterms:description: The scope of a resource is a URI for the resource's OSLC Service Provider.
- SpecIF:Origin: http://open-services.net/bin/view/Main/RmSpecificationV2

## oslc:instanceShape (Property-Term)
- dcterms:description: Resource Shape that provides hints as to resource property value-types and allowed values.
- SpecIF:Origin: http://open-services.net/bin/view/Main/RmSpecificationV2

## oslc_rm:elaboratedBy (Property-Term)
- dcterms:description: The subject is elaborated by the object.
- SpecIF:Origin: http://open-services.net/bin/view/Main/RmSpecificationV2

## oslc_rm:elaborates (Property-Term)
- dcterms:description: The object is elaborated by the subject. For example, a use case elaborates a requirement.
- SpecIF:Origin: http://open-services.net/bin/view/Main/RmSpecificationV2

## oslc_rm:specifiedBy (Property-Term)
- dcterms:description: The subject is specified by the object.
- SpecIF:Origin: http://open-services.net/bin/view/Main/RmSpecificationV2

## oslc_rm:specifies (Property-Term)
- dcterms:description: The object is specified by the subject. For example, a requirement specifies a model element.
- SpecIF:Origin: http://open-services.net/bin/view/Main/RmSpecificationV2

## oslc_rm:affectedBy (Property-Term)
- dcterms:description: Requirement is affected by a resource, such as a defect or issue.
- SpecIF:Origin: http://open-services.net/bin/view/Main/RmSpecificationV2

## oslc_rm:trackedBy (Property-Term)
- dcterms:description: Resource, such as a change request, which tracks this requirement.
- SpecIF:Origin: http://open-services.net/bin/view/Main/RmSpecificationV2

## oslc_rm:implementedBy (Property-Term)
- dcterms:description: Resource, such as a change request, which implements this requirement.
- SpecIF:Origin: http://open-services.net/bin/view/Main/RmSpecificationV2

## oslc_rm:validatedBy (Property-Term)
- dcterms:description: Resource, such as a test case, which validates this requirement.
- SpecIF:Origin: http://open-services.net/bin/view/Main/RmSpecificationV2

## oslc_rm:decomposedBy (Property-Term)
- dcterms:description: The subject is decomposed by the object.
- SpecIF:Origin: http://open-services.net/bin/view/Main/RmSpecificationV2

## oslc_rm:decomposes (Property-Term)
- dcterms:description: The object is decomposed by the subject. For example, a collection of subsystems decomposes a system.
- SpecIF:Origin: http://open-services.net/bin/view/Main/RmSpecificationV2

## oslc_rm:constrainedBy (Property-Term)
- dcterms:description: The subject is constrained by the object.
- SpecIF:Origin: http://open-services.net/bin/view/Main/RmSpecificationV2

## oslc_rm:constrains (Property-Term)
- dcterms:description: The object is constrained by the subject. For example, a safety requirement constrains a functional requirement.
- SpecIF:Origin: http://open-services.net/bin/view/Main/RmSpecificationV2

## SpecIF:Type (Property-Term)
- SpecIF:Origin: http://specif.de
- SpecIF:Status: preferred

## SpecIF:Category (Property-Term)
- dcterms:description: The 'Category' (class) of the resource, usually with an enumerated value.
  Useful categories for requirements have been defined by the IREB, namely 'Function', 'Quality' and 'Constraint'.
- SpecIF:Origin: http://specif.de
- SpecIF:Status: preferred

## SpecIF:Notation (Property-Term)
- dcterms:description: The notation used by a model diagram, e.g. 'BPMN 2.0', 'SysML Activity Diagram' or 'FMC Block Diagram'.
- SpecIF:Origin: http://specif.de
- SpecIF:Status: preferred

## SpecIF:Stereotype (Property-Term)
- dcterms:description: Describes the role or sub-type of a model-element. For example, a [[FMC:Actor]] may represent a System Function, a System Component or a User Role. Similarly, in the context of process modelling, a FMC:Actor may represent a Process Step or again a User Role. So, all of these are meaningful values for a FMC:Actor's property named SpecIF:Stereotype.
- SpecIF:Origin: http://specif.de
- SpecIF:Status: deprecated

## dcterms:type (Property-Term)
- dcterms:description: The nature or genre of the resource. (source: DCMI)
  Recommended best practice is to use a controlled vocabulary such as the DCMI Type Vocabulary [DCMITYPE]. To describe the file format, physical medium, or dimensions of the resource, use the Format element.
  For example, a [[FMC:Actor]] may represent a System Function, a System Component or a User Role. Similarly, in the context of process modelling, a FMC:Actor may represent a Process Step or again a User Role. So, all of these are meaningful values for a FMC:Actor's property named dcterms:type.
- SpecIF:Origin: http://dublincore.org/specifications/
- SpecIF:Status: experimental

## SpecIF:SubClass (Property-Term)
- dcterms:description: Describes the role or sub-type of a model-element. For example, a [[FMC:Actor]] may represent a System Function, a System Component or a User Role. Similarly, in the context of process modelling, a FMC:Actor may represent a Process Step or again a User Role. So, all of these are meaningful values for a FMC:Actor's property named SpecIF:SubClass.
- SpecIF:Origin: http://specif.de
- SpecIF:Status: deprecated

## SpecIF:Status (Property-Term)
- dcterms:description: The 'Status', e.g. lifecycle state, of the resource.
- SpecIF:Origin: http://specif.de
- SpecIF:Status: preferred

## SpecIF:Probability (Property-Term)
- SpecIF:Origin: http://specif.de
- SpecIF:Status: preferred

## SpecIF:Priority (Property-Term)
- dcterms:description: The 'Priority' of the resource.
- SpecIF:Origin: http://specif.de
- SpecIF:Status: preferred

## SpecIF:Responsible (Property-Term)
- dcterms:description: The 'Person' being responsible for the resource.
- SpecIF:Origin: http://specif.de
- SpecIF:Status: preferred

## SpecIF:Milestone (Property-Term)
- dcterms:description: A target 'Milestone' to implement the resource.
- SpecIF:Origin: http://specif.de
- SpecIF:Status: preferred

## SpecIF:DueDate (Property-Term)
- dcterms:description: A 'Due Date' for the resource.
- SpecIF:Origin: http://specif.de
- SpecIF:Status: preferred

## SpecIF:Benefit (Property-Term)
- SpecIF:Origin: http://specif.de
- SpecIF:Status: preferred

## SpecIF:Damage (Property-Term)
- SpecIF:Origin: http://specif.de
- SpecIF:Status: preferred

## SpecIF:Icon (Property-Term)
- dcterms:description: An icon associated with the resource class.
- SpecIF:Origin: http://specif.de
- SpecIF:Status: preferred

## SpecIF:Tag (Property-Term)
- SpecIF:Origin: http://specif.de
- SpecIF:Status: preferred

## SpecIF:Instantiation (Property-Term)
- dcterms:description: "user": a user creates, updates and deletes a resource's instance manually.
  "auto": a resource's instance is created, updated or deleted by an algorithm.
- SpecIF:Origin: http://specif.de
- SpecIF:Status: preferred

## SpecIF:Creation (Property-Term)
- dcterms:description: "manual": user interface supports creation, update and deletion of the resource.
  "auto": the resource is created, updated or deleted by an algorithm.
- SpecIF:Origin: http://specif.de
- SpecIF:Status: deprecated

## SpecIF:Origin (Property-Term)
- dcterms:description: The origin (source, reference) of an information or requirement
- SpecIF:Origin: http://specif.de
- SpecIF:Status: preferred

## SpecIF:Subject (Property-Term)
- dcterms:description: The subject of a subject-predicate-object statement. Corresponds to a 'source' in ReqIF terminology.
- SpecIF:Origin: http://specif.de
- SpecIF:Status: preferred

## SpecIF:Source (Property-Term)
- dcterms:description: The subject of a subject-predicate-object statement.
- SpecIF:Origin: http://specif.de
- SpecIF:Status: deprecated

## SpecIF:Object (Property-Term)
- dcterms:description: The object of a subject-predicate-object statement. Corresponds to a 'target' in ReqIF terminology.
- SpecIF:Origin: http://specif.de
- SpecIF:Status: preferred

## SpecIF:Target (Property-Term)
- dcterms:description: The object of a subject-predicate-object statement.
- SpecIF:Origin: http://specif.de
- SpecIF:Status: deprecated

## SpecIF:FitCriteria (Property-Term)
- SpecIF:Origin: http://specif.de
- SpecIF:Status: preferred

## SpecIF:OrdinalMark (Property-Term)
- dcterms:description: A string to determine the ordering of elements. Rules:
  - For ordering, only alphanumeric characters are permissible. A letter case has no effect; for example, 'F' is equivalent to 'f'.
  - The ordering at character level is alphanumeric, i.e. '1' < '7' < 'D' < 'X'.
  - Single character substrings < two-character substrings < substrings with more characters, thus '9' < '12' < '114'.
  - The ordinal mark may be separated by non-alphanumeric characters. All separators are equivalent; e.g. '-' is equivalent to ';' or '/'.
  - Each alphanumeric substring is used for ordering on its hierarchical level; the leftmost substring is most significant for the overall ordering.
  - For example '1' < '1.2' < '1.Y' < '1.1a' < '1-1b' < '1-1C' < '2'.
  A regular expression for extracting the substrings of an ordinal mark is /([0-9a-z]+)[^0-9a-z]{0,1}/gi.
- SpecIF:Origin: http://specif.de
- SpecIF:Status: experimental

## HIS:OemComment (Property-Term)
- SpecIF:Origin: Hersteller-Initiative Software
- SpecIF:Status: preferred

## HIS:OemStatus (Property-Term)
- SpecIF:Origin: Hersteller-Initiative Software
- SpecIF:Status: preferred

## HIS:SupplierComment (Property-Term)
- SpecIF:Origin: Hersteller-Initiative Software
- SpecIF:Status: preferred

## HIS:SupplierStatus (Property-Term)
- SpecIF:Origin: Hersteller-Initiative Software
- SpecIF:Status: preferred

## SpecIF:priorityHigh (Value-Term)
- dcterms:description: A value for property [[SpecIF:Priority]].
- SpecIF:Origin: http://specif.de
- SpecIF:Status: experimental

## SpecIF:priorityRatherHigh (Value-Term)
- dcterms:description: A value for property [[SpecIF:Priority]].
- SpecIF:Origin: http://specif.de
- SpecIF:Status: experimental

## SpecIF:priorityMedium (Value-Term)
- dcterms:description: A value for property [[SpecIF:Priority]].
- SpecIF:Origin: http://specif.de
- SpecIF:Status: experimental

## SpecIF:priorityRatherLow (Value-Term)
- dcterms:description: A value for property [[SpecIF:Priority]].
- SpecIF:Origin: http://specif.de
- SpecIF:Status: experimental

## SpecIF:priorityLow (Value-Term)
- dcterms:description: A value for property [[SpecIF:Priority]].
- SpecIF:Origin: http://specif.de
- SpecIF:Status: experimental

## SpecIF:sizeXL (Value-Term)
- dcterms:description: T-shirt sizes have become popular to classify [[IREB:Risk]], [[SpecIF:Damage]] or similar. Translates to 'very large' in English.
- SpecIF:Origin: http://specif.de
- SpecIF:Status: experimental

## SpecIF:sizeL (Value-Term)
- dcterms:description: T-shirt sizes have become popular to classify [[IREB:Risk]], [[SpecIF:Damage]] or similar. Translates to 'large' in English.
- SpecIF:Origin: http://specif.de
- SpecIF:Status: experimental

## SpecIF:sizeM (Value-Term)
- dcterms:description: T-shirt sizes have become popular to classify [[IREB:Risk]], [[SpecIF:Damage]] or similar. Translates to 'medium' in English.
- SpecIF:Origin: http://specif.de
- SpecIF:Status: experimental

## SpecIF:sizeS (Value-Term)
- dcterms:description: T-shirt sizes have become popular to classify [[IREB:Risk]], [[SpecIF:Damage]] or similar. Translates to 'small' in English.
- SpecIF:Origin: http://specif.de
- SpecIF:Status: experimental

## SpecIF:sizeXS (Value-Term)
- dcterms:description: T-shirt sizes have become popular to classify [[IREB:Risk]], [[SpecIF:Damage]] or similar. Translates to 'very small' in English.
- SpecIF:Origin: http://specif.de
- SpecIF:Status: experimental

## IREB:Stakeholder (Resource-Term)
- dcterms:description: A person or organization that has a (direct or indirect) influence on a system’s requirements. Indirect influence also includes situations where a person or organization is impacted by the system. (source: IREB CPRE Glossary)
  This is a subclass of [[FMC:Actor]], more precisely a value of it's property [[dcterms:type]].
- SpecIF:Origin: https://www.ireb.org/content/downloads/1-cpre-glossary/ireb_cpre_glossary_17.pdf
- SpecIF:Status: preferred

## SpecIF:UserRole (Resource-Term)
- dcterms:description: This is a subclass of [[FMC:Actor]]; more precisely a value of it's property [[dcterms:type]].
- SpecIF:Status: experimental

## BPMN:StartEvent (Value-Term)
- dcterms:description: A defined value for the [[dcterms:type]] property of [[FMC:Event]] when used to represent a general start event.
- SpecIF:Origin: https://camunda.com/bpmn/reference/
- SpecIF:Status: experimental

## BPMN:IntermediateEvent (Value-Term)
- dcterms:description: A defined value for the [[dcterms:type]] property of [[FMC:Event]] when used to represent a general intermediate event.
- SpecIF:Origin: https://camunda.com/bpmn/reference/
- SpecIF:Status: experimental

## BPMN:EndEvent (Value-Term)
- dcterms:description: A defined value for the [[dcterms:type]] property of [[FMC:Event]] when used to represent a general end event.
- SpecIF:Origin: https://camunda.com/bpmn/reference/
- SpecIF:Status: experimental

## BPMN:ProcessStep (Value-Term)
- dcterms:description: A defined value for the [[dcterms:type]] property of [[FMC:Actor]] when used to represent a process step.
- SpecIF:Status: experimental

## BPMN:Join (Value-Term)
- dcterms:description: A defined value for the [[dcterms:type]] property of [[FMC:Actor]] when used to represent a 'Join' element in models created with BPMN.
- SpecIF:Status: experimental

## BPMN:Timer (Value-Term)
- dcterms:description: A defined value for the [[dcterms:type]] property of [[FMC:Actor]] when used to represent a 'Timer' element in models created with BPMN.
- SpecIF:Status: experimental

## SpecIF Vocabulary (SpecIF:Hierarchy)

## Statements
- FMC:Plan SpecIF:isSynonymOf SpecIF:Diagram
- SpecIF:View SpecIF:isSynonymOf SpecIF:Diagram
- SpecIF:Collection SpecIF:isSynonymOf BPMN:Group
- SpecIF:satisfies SpecIF:isSynonymOf oslc_rm:satisfies
- SpecIF:Stereotype SpecIF:isSynonymOf dcterms:type
- SpecIF:SubClass SpecIF:isSynonymOf dcterms:type
- oslc_rm:satisfiedBy SpecIF:isInverseOf oslc_rm:satisfies
- oslc_rm:elaboratedBy SpecIF:isInverseOf oslc_rm:elaborates
- oslc_rm:specifiedBy SpecIF:isInverseOf oslc_rm:specifies
- oslc_rm:decomposedBy SpecIF:isInverseOf oslc_rm:decomposes
- oslc_rm:constrainedBy SpecIF:isInverseOf oslc_rm:constrains
- SpecIF:follows SpecIF:isInverseOf SpecIF:precedes
- SysML:isGeneralisationOf SpecIF:isInverseOf SysML:isSpecialisationOf
- SpecIF:sameAs SpecIF:isSynonymOf owl:sameAs
- SpecIF:Outline SpecIF:isSynonymOf SpecIF:Hierarchy
- SpecIF:Id SpecIF:isSynonymOf dcterms:identifier
- SpecIF:createdBy SpecIF:isSynonymOf dcterms:creator
- SpecIF:createdAt SpecIF:isSynonymOf dcterms:created
- SpecIF:changedAt SpecIF:isSynonymOf dcterms:modified
- SpecIF:Creation SpecIF:isSynonymOf SpecIF:Instantiation
- SpecIF:Source SpecIF:isSynonymOf SpecIF:Subject
- SpecIF:Target SpecIF:isSynonymOf SpecIF:Object
- SpecIF:actorInheritsFrom SpecIF:isSpecialisationOf SpecIF:inheritsFrom
- SpecIF:stateInheritsFrom SpecIF:isSpecialisationOf SpecIF:inheritsFrom
- SpecIF:eventInheritsFrom SpecIF:isSpecialisationOf SpecIF:inheritsFrom
